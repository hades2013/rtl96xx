--
-- 
-- MIB generated by MG-SOFT Visual MIB Builder Version 6.0  Build 88
-- Friday, March 01, 2013 at 09:44:16
--

--  
-- MIB generated by MG-SOFT Visual MIB Builder Version 6.0  Build 88
-- Thursday, January 31, 2013 at 22:50:43
-- 
--  
-- MIB generated by MG-SOFT Visual MIB Builder Version 6.0  Build 88
-- Thursday, January 31, 2013 at 10:54:12
-- 
--  
-- MIB generated by MG-SOFT Visual MIB Builder Version 6.0  Build 88
-- Sunday, January 20, 2013 at 20:07:42
-- 
--  
-- MIB generated by MG-SOFT Visual MIB Builder Version 6.0  Build 88
-- Saturday, January 19, 2013 at 15:19:35
-- 
--  
-- MIB generated by MG-SOFT Visual MIB Builder Version 6.0  Build 88
-- Friday, January 18, 2013 at 15:53:59
-- 
--  
-- MIB generated by MG-SOFT Visual MIB Builder Version 6.0  Build 88
-- Friday, January 18, 2013 at 14:27:46
-- 
--  
-- MIB generated by MG-SOFT Visual MIB Builder Version 6.0  Build 88
-- Monday, January 07, 2013 at 10:58:52
-- 
--  
-- MIB generated by MG-SOFT Visual MIB Builder Version 6.0  Build 88
-- Tuesday, December 11, 2012 at 13:36:48
-- 
-- 
-- This MIB module has been converted from SMIv1 to SMIv2 format by
-- MG-SOFT Visual MIB Builder.
-- 
-- Caution: There are differences in values and use of SMIv1 and SMIv2
-- STATUS and ACCESS/MAX-ACCESS clauses. When a MIB module is mechanically
-- translated from SMIv1 to SMIv2 format, the STATUS and ACCESS clause
-- values cannot always be appropriately converted.
-- 
-- * The SMIv1 STATUS clause values specify two attributes of object
--   definitions: the validity of the object definition and the implementation
--   conformance requirements. The SMIv2 STATUS clause values specify only
--   the validity of the object definition, while the conformance requirements
--   can be defined with the MODULE-COMPLIANCE statements.
-- 
-- * In SMIv1, the ACCESS clause specifies the minimal required access,
--   while in SMIv2, the MAX-ACCESS clause specifies the maximum allowed access.
--   This should be considered when converting an ACCESS clause to a MAX-ACCESS clause.
-- 
-- You should carefully check all STATUS and MAX-ACCESS clause values of OBJECT-TYPE
-- definitions in this module and modify them or add a note into DECRIPTION clause
-- if necessary. For details about the rules for converting MIB modules from SMIv1 to
-- SMIv2 format, see the RFC 3584 (section 2.1.1), or "Understanding SNMP MIBs"
-- book by D.T. Perkins and E. McGinnis (section 8.2).
-- 

	EPN104-MIB DEFINITIONS ::= BEGIN
 
		IMPORTS
			IANAifType			
				FROM IANAifType-MIB			
			internet, enterprises, TimeTicks, IpAddress, Integer32, 
			Gauge32, Counter32, OBJECT-TYPE, MODULE-IDENTITY, OBJECT-IDENTITY, 
			NOTIFICATION-TYPE			
				FROM SNMPv2-SMI			
			TimeStamp, PhysAddress, TEXTUAL-CONVENTION			
				FROM SNMPv2-TC;
	
	
--         1.3.6.1.4.1.1
-- December 11, 2012 at 11:40 GMT
-- 1.3.6.1.4.1.17409
-- December 11, 2012 at 11:40 GMT
-- 1.3.6.1.4.1.17409
-- December 11, 2012 at 11:40 GMT
-- 1.3.6.1.4.1.17409
-- December 11, 2012 at 11:40 GMT
-- 1.3.6.1.4.1.17409
-- December 11, 2012 at 11:40 GMT
-- 1.3.6.1.4.1.17409
-- December 11, 2012 at 11:40 GMT
-- 1.3.6.1.4.1.17409
-- December 11, 2012 at 11:40 GMT
-- 1.3.6.1.4.1.17409
-- December 11, 2012 at 11:40 GMT
		-- 1.3.6.1.4.1.17409
		nscrtvRoot MODULE-IDENTITY 
			LAST-UPDATED "201212111140Z"		-- December 11, 2012 at 11:40 GMT
			ORGANIZATION 
				"Your organization"
			CONTACT-INFO 
				"Your contact info"
			DESCRIPTION 
				"Enter the description for this MIB module."
			::= { enterprises 17409 }

		
	
--
-- Type definitions
--
	
--  Type definitions
-- 
-- Type definitions
-- 
-- Type definitions
-- 
-- Type definitions
-- 
-- Type definitions
-- 
-- Type definitions
-- 
-- Type definitions
-- 
-- Type definitions
-- 
-- Type definitions  feihuaxin
-- 
		DisplayString ::= OCTET STRING

	
--
-- Textual conventions
--
	
--  Textual conventions
-- 
-- Textual conventions
-- 
-- Textual conventions
-- 
-- Textual conventions
-- 
-- Textual conventions
-- 
-- Textual conventions
-- 
-- Textual conventions
-- 
-- InterfaceIndex contains the semantics of ifIndex and should be used
-- for any objects defined in other MIB modules that need these semantics.
		InterfaceIndex ::= TEXTUAL-CONVENTION
			DISPLAY-HINT 
				"d"
			STATUS current
			DESCRIPTION 
				"A unique value, greater than zero, for each interface or
				interface sub-layer in the managed system.  It is
				recommended that values are assigned contiguously starting
				from 1.  The value for each interface sub-layer must remain
				constant at least from one re-initialization of the entity's
				network management system to the next re-initialization."
			SYNTAX Integer32 (1..2147483647)

	
--
-- Node definitions
--
	
--  Node definitions
-- 
-- Node definitions
-- 
-- Node definitions
-- 
-- Node definitions
-- 
-- Node definitions
-- 
-- Node definitions
-- 
-- Node definitions
-- 
-- Node definitions
-- 
-- 1.3.6.1.2
-- 1.3.6.1.2
-- 1.3.6.1.2
-- 1.3.6.1.2
-- 1.3.6.1.2
-- 1.3.6.1.2
-- 1.3.6.1.2
-- 1.3.6.1.2
		-- 1.3.6.1.2
		mgmt OBJECT IDENTIFIER ::= { internet 2 }

		
--         1.3.6.1.2.1
-- 1.3.6.1.2.1
-- 1.3.6.1.2.1
-- 1.3.6.1.2.1
-- 1.3.6.1.2.1
-- 1.3.6.1.2.1
-- 1.3.6.1.2.1
-- 1.3.6.1.2.1
		-- 1.3.6.1.2.1
		mib-2 OBJECT IDENTIFIER ::= { mgmt 1 }

		
--           ::= { snmpMIBObjects 1 }        this OID is obsolete
-- ::= { snmpMIBObjects 2 }        this OID is obsolete
-- ::= { snmpMIBObjects 3 }        this OID is obsolete
-- the System group
-- 
-- a collection of objects common to all managed systems.
-- 1.3.6.1.2.1.1
-- 1.3.6.1.2.1.1
-- 1.3.6.1.2.1.1
-- 1.3.6.1.2.1.1
-- 1.3.6.1.2.1.1
-- 1.3.6.1.2.1.1
-- 1.3.6.1.2.1.1
-- 1.3.6.1.2.1.1
		-- 1.3.6.1.2.1.1
		system OBJECT IDENTIFIER ::= { mib-2 1 }

		
--         1.3.6.1.2.1.1.1
-- 1.3.6.1.2.1.1.1
-- 1.3.6.1.2.1.1.1
-- 1.3.6.1.2.1.1.1
-- 1.3.6.1.2.1.1.1
-- 1.3.6.1.2.1.1.1
-- 1.3.6.1.2.1.1.1
-- 1.3.6.1.2.1.1.1
		-- 1.3.6.1.2.1.1.1
		sysDescr OBJECT-TYPE
			SYNTAX DisplayString (SIZE (0..255))
			MAX-ACCESS read-only
			STATUS current
			DESCRIPTION
				"A textual description of the entity.  This value should
				include the full name and version identification of
				the system's hardware type, software operating-system,
				and networking software."
			::= { system 1 }

		
--         1.3.6.1.2.1.1.2
-- 1.3.6.1.2.1.1.2
-- 1.3.6.1.2.1.1.2
-- 1.3.6.1.2.1.1.2
-- 1.3.6.1.2.1.1.2
-- 1.3.6.1.2.1.1.2
-- 1.3.6.1.2.1.1.2
-- 1.3.6.1.2.1.1.2
		-- 1.3.6.1.2.1.1.2
		sysObjectID OBJECT-TYPE
			SYNTAX OBJECT IDENTIFIER
			MAX-ACCESS read-only
			STATUS current
			DESCRIPTION
				"The vendor's authoritative identification of the
				network management subsystem contained in the entity.
				This value is allocated within the SMI enterprises
				subtree (1.3.6.1.4.1) and provides an easy and
				unambiguous means for determining `what kind of box' is
				being managed.  For example, if vendor `Flintstones,
				Inc.' was assigned the subtree 1.3.6.1.4.1.424242,
				it could assign the identifier 1.3.6.1.4.1.424242.1.1
				to its `Fred Router'."
			::= { system 2 }

		
--         1.3.6.1.2.1.1.3
-- 1.3.6.1.2.1.1.3
-- 1.3.6.1.2.1.1.3
-- 1.3.6.1.2.1.1.3
-- 1.3.6.1.2.1.1.3
-- 1.3.6.1.2.1.1.3
-- 1.3.6.1.2.1.1.3
-- 1.3.6.1.2.1.1.3
		-- 1.3.6.1.2.1.1.3
		sysUpTime OBJECT-TYPE
			SYNTAX TimeTicks
			MAX-ACCESS read-only
			STATUS current
			DESCRIPTION
				"The time (in hundredths of a second) since the
				network management portion of the system was last
				re-initialized."
			::= { system 3 }

		
--         1.3.6.1.2.1.1.4
-- 1.3.6.1.2.1.1.4
-- 1.3.6.1.2.1.1.4
-- 1.3.6.1.2.1.1.4
-- 1.3.6.1.2.1.1.4
-- 1.3.6.1.2.1.1.4
-- 1.3.6.1.2.1.1.4
-- 1.3.6.1.2.1.1.4
		-- 1.3.6.1.2.1.1.4
		sysContact OBJECT-TYPE
			SYNTAX DisplayString (SIZE (0..255))
			MAX-ACCESS read-write
			STATUS current
			DESCRIPTION
				"The textual identification of the contact person for
				this managed node, together with information on how
				to contact this person.  If no contact information is
				known, the value is the zero-length string."
			::= { system 4 }

		
--         1.3.6.1.2.1.1.5
-- 1.3.6.1.2.1.1.5
-- 1.3.6.1.2.1.1.5
-- 1.3.6.1.2.1.1.5
-- 1.3.6.1.2.1.1.5
-- 1.3.6.1.2.1.1.5
-- 1.3.6.1.2.1.1.5
-- 1.3.6.1.2.1.1.5
		-- 1.3.6.1.2.1.1.5
		sysName OBJECT-TYPE
			SYNTAX DisplayString (SIZE (0..255))
			MAX-ACCESS read-write
			STATUS current
			DESCRIPTION
				"An administratively-assigned name for this managed
				node.  By convention, this is the node's fully-qualified
				domain name.  If the name is unknown, the value is
				the zero-length string."
			::= { system 5 }

		
--         1.3.6.1.2.1.1.6
-- 1.3.6.1.2.1.1.6
-- 1.3.6.1.2.1.1.6
-- 1.3.6.1.2.1.1.6
-- 1.3.6.1.2.1.1.6
-- 1.3.6.1.2.1.1.6
-- 1.3.6.1.2.1.1.6
-- 1.3.6.1.2.1.1.6
		-- 1.3.6.1.2.1.1.6
		sysLocation OBJECT-TYPE
			SYNTAX DisplayString (SIZE (0..255))
			MAX-ACCESS read-write
			STATUS current
			DESCRIPTION
				"The physical location of this node (e.g., 'telephone
				closet, 3rd floor').  If the location is unknown, the
				value is the zero-length string."
			::= { system 6 }

		
--         1.3.6.1.2.1.1.7
-- 1.3.6.1.2.1.1.7
-- 1.3.6.1.2.1.1.7
-- 1.3.6.1.2.1.1.7
-- 1.3.6.1.2.1.1.7
-- 1.3.6.1.2.1.1.7
-- 1.3.6.1.2.1.1.7
-- 1.3.6.1.2.1.1.7
		-- 1.3.6.1.2.1.1.7
		sysServices OBJECT-TYPE
			SYNTAX INTEGER (0..127)
			MAX-ACCESS read-only
			STATUS current
			DESCRIPTION
				"A value which indicates the set of services that this
				entity may potentially offer.  The value is a sum.
				
				
				This sum initially takes the value zero. Then, for
				each layer, L, in the range 1 through 7, that this node
				performs transactions for, 2 raised to (L - 1) is added
				to the sum.  For example, a node which performs only
				routing functions would have a value of 4 (2^(3-1)).
				In contrast, a node which is a host offering application
				services would have a value of 72 (2^(4-1) + 2^(7-1)).
				Note that in the context of the Internet suite of
				protocols, values should be calculated accordingly:
				
				     layer      functionality
				       1        physical (e.g., repeaters)
				       2        datalink/subnetwork (e.g., bridges)
				       3        internet (e.g., supports the IP)
				       4        end-to-end  (e.g., supports the TCP)
				       7        applications (e.g., supports the SMTP)
				
				For systems including OSI protocols, layers 5 and 6
				may also be counted."
			::= { system 7 }

		
--          object resource information
-- 
-- a collection of objects which describe the SNMP entity's
-- (statically and dynamically configurable) support of
-- various MIB modules.
-- 1.3.6.1.2.1.1.8
-- 1.3.6.1.2.1.1.8
-- 1.3.6.1.2.1.1.8
-- 1.3.6.1.2.1.1.8
-- 1.3.6.1.2.1.1.8
-- 1.3.6.1.2.1.1.8
-- 1.3.6.1.2.1.1.8
-- 1.3.6.1.2.1.1.8
		-- 1.3.6.1.2.1.1.8
		sysORLastChange OBJECT-TYPE
			SYNTAX TimeStamp
			MAX-ACCESS read-only
			STATUS current
			DESCRIPTION
				"The value of sysUpTime at the time of the most recent
				change in state or value of any instance of sysORID."
			::= { system 8 }

		
--         1.3.6.1.2.1.1.9
-- 1.3.6.1.2.1.1.9
-- 1.3.6.1.2.1.1.9
-- 1.3.6.1.2.1.1.9
-- 1.3.6.1.2.1.1.9
-- 1.3.6.1.2.1.1.9
-- 1.3.6.1.2.1.1.9
-- 1.3.6.1.2.1.1.9
		-- 1.3.6.1.2.1.1.9
		sysORTable OBJECT-TYPE
			SYNTAX SEQUENCE OF SysOREntry
			MAX-ACCESS not-accessible
			STATUS current
			DESCRIPTION
				"The (conceptual) table listing the capabilities of
				the local SNMP application acting as a command
				responder with respect to various MIB modules.
				SNMP entities having dynamically-configurable support
				of MIB modules will have a dynamically-varying number
				of conceptual rows."
			::= { system 9 }

		
--         1.3.6.1.2.1.1.9.1
-- 1.3.6.1.2.1.1.9.1
-- 1.3.6.1.2.1.1.9.1
-- 1.3.6.1.2.1.1.9.1
-- 1.3.6.1.2.1.1.9.1
-- 1.3.6.1.2.1.1.9.1
-- 1.3.6.1.2.1.1.9.1
-- 1.3.6.1.2.1.1.9.1
		-- 1.3.6.1.2.1.1.9.1
		sysOREntry OBJECT-TYPE
			SYNTAX SysOREntry
			MAX-ACCESS not-accessible
			STATUS current
			DESCRIPTION
				"An entry (conceptual row) in the sysORTable."
			INDEX { sysORIndex }
			::= { sysORTable 1 }

		
		SysOREntry ::=
			SEQUENCE { 
				sysORIndex
					INTEGER,
				sysORID
					OBJECT IDENTIFIER,
				sysORDescr
					DisplayString,
				sysORUpTime
					TimeStamp
			 }

--         1.3.6.1.2.1.1.9.1.1
-- 1.3.6.1.2.1.1.9.1.1
-- 1.3.6.1.2.1.1.9.1.1
-- 1.3.6.1.2.1.1.9.1.1
-- 1.3.6.1.2.1.1.9.1.1
-- 1.3.6.1.2.1.1.9.1.1
-- 1.3.6.1.2.1.1.9.1.1
-- 1.3.6.1.2.1.1.9.1.1
		-- 1.3.6.1.2.1.1.9.1.1
		sysORIndex OBJECT-TYPE
			SYNTAX INTEGER (1..2147483647)
			MAX-ACCESS not-accessible
			STATUS current
			DESCRIPTION
				"The auxiliary variable used for identifying instances
				of the columnar objects in the sysORTable."
			::= { sysOREntry 1 }

		
--         1.3.6.1.2.1.1.9.1.2
-- 1.3.6.1.2.1.1.9.1.2
-- 1.3.6.1.2.1.1.9.1.2
-- 1.3.6.1.2.1.1.9.1.2
-- 1.3.6.1.2.1.1.9.1.2
-- 1.3.6.1.2.1.1.9.1.2
-- 1.3.6.1.2.1.1.9.1.2
-- 1.3.6.1.2.1.1.9.1.2
		-- 1.3.6.1.2.1.1.9.1.2
		sysORID OBJECT-TYPE
			SYNTAX OBJECT IDENTIFIER
			MAX-ACCESS read-only
			STATUS current
			DESCRIPTION
				"An authoritative identification of a capabilities
				statement with respect to various MIB modules supported
				by the local SNMP application acting as a command
				responder."
			::= { sysOREntry 2 }

		
--         1.3.6.1.2.1.1.9.1.3
-- 1.3.6.1.2.1.1.9.1.3
-- 1.3.6.1.2.1.1.9.1.3
-- 1.3.6.1.2.1.1.9.1.3
-- 1.3.6.1.2.1.1.9.1.3
-- 1.3.6.1.2.1.1.9.1.3
-- 1.3.6.1.2.1.1.9.1.3
-- 1.3.6.1.2.1.1.9.1.3
		-- 1.3.6.1.2.1.1.9.1.3
		sysORDescr OBJECT-TYPE
			SYNTAX DisplayString
			MAX-ACCESS read-only
			STATUS current
			DESCRIPTION
				"A textual description of the capabilities identified
				by the corresponding instance of sysORID."
			::= { sysOREntry 3 }

		
--         1.3.6.1.2.1.1.9.1.4
-- 1.3.6.1.2.1.1.9.1.4
-- 1.3.6.1.2.1.1.9.1.4
-- 1.3.6.1.2.1.1.9.1.4
-- 1.3.6.1.2.1.1.9.1.4
-- 1.3.6.1.2.1.1.9.1.4
-- 1.3.6.1.2.1.1.9.1.4
-- 1.3.6.1.2.1.1.9.1.4
		-- 1.3.6.1.2.1.1.9.1.4
		sysORUpTime OBJECT-TYPE
			SYNTAX TimeStamp
			MAX-ACCESS read-only
			STATUS current
			DESCRIPTION
				"The value of sysUpTime at the time this conceptual
				row was last instantiated."
			::= { sysOREntry 4 }

		
--        1.3.6.1.2.1.2
-- 1.3.6.1.2.1.2
-- 1.3.6.1.2.1.2
-- 1.3.6.1.2.1.2
-- 1.3.6.1.2.1.2
-- 1.3.6.1.2.1.2
-- 1.3.6.1.2.1.2
		-- 1.3.6.1.2.1.2
		interfaces OBJECT IDENTIFIER ::= { mib-2 2 }

		
--        1.3.6.1.2.1.2.1
-- 1.3.6.1.2.1.2.1
-- 1.3.6.1.2.1.2.1
-- 1.3.6.1.2.1.2.1
-- 1.3.6.1.2.1.2.1
-- 1.3.6.1.2.1.2.1
-- 1.3.6.1.2.1.2.1
		-- 1.3.6.1.2.1.2.1
		ifNumber OBJECT-TYPE
			SYNTAX Integer32
			MAX-ACCESS read-only
			STATUS current
			DESCRIPTION
				"The number of network interfaces (regardless of their
				current state) present on this system."
			::= { interfaces 1 }

		
--         the Interfaces table
-- The Interfaces table contains information on the entity's
-- interfaces.  Each sub-layer below the internetwork-layer
-- of a network interface is considered to be an interface.
-- 1.3.6.1.2.1.2.2
-- 1.3.6.1.2.1.2.2
-- 1.3.6.1.2.1.2.2
-- 1.3.6.1.2.1.2.2
-- 1.3.6.1.2.1.2.2
-- 1.3.6.1.2.1.2.2
-- 1.3.6.1.2.1.2.2
		-- 1.3.6.1.2.1.2.2
		ifTable OBJECT-TYPE
			SYNTAX SEQUENCE OF IfEntry
			MAX-ACCESS not-accessible
			STATUS current
			DESCRIPTION
				"A list of interface entries.  The number of entries is
				given by the value of ifNumber."
			::= { interfaces 2 }

		
--        1.3.6.1.2.1.2.2.1
-- 1.3.6.1.2.1.2.2.1
-- 1.3.6.1.2.1.2.2.1
-- 1.3.6.1.2.1.2.2.1
-- 1.3.6.1.2.1.2.2.1
-- 1.3.6.1.2.1.2.2.1
-- 1.3.6.1.2.1.2.2.1
		-- 1.3.6.1.2.1.2.2.1
		ifEntry OBJECT-TYPE
			SYNTAX IfEntry
			MAX-ACCESS not-accessible
			STATUS current
			DESCRIPTION
				"An entry containing management information applicable to a
				particular interface."
			INDEX { ifIndex }
			::= { ifTable 1 }

		
		IfEntry ::=
			SEQUENCE { 
				ifIndex
					InterfaceIndex,
				ifDescr
					DisplayString,
				ifType
					IANAifType,
				ifMtu
					Integer32,
				ifSpeed
					Gauge32,
				ifPhysAddress
					PhysAddress,
				ifAdminStatus
					INTEGER,
				ifOperStatus
					INTEGER,
				ifLastChange
					TimeTicks,
				ifInOctets
					Counter32,
				ifInUcastPkts
					Counter32,
				ifInNUcastPkts
					Counter32,
				ifInDiscards
					Counter32,
				ifInErrors
					Counter32,
				ifInUnknownProtos
					Counter32,
				ifOutOctets
					Counter32,
				ifOutUcastPkts
					Counter32,
				ifOutNUcastPkts
					Counter32,
				ifOutDiscards
					Counter32,
				ifOutErrors
					Counter32,
				ifOutQLen
					Gauge32,
				ifSpecific
					OBJECT IDENTIFIER
			 }

--         deprecated
-- deprecated
-- deprecated
-- deprecated
-- 1.3.6.1.2.1.2.2.1.1
-- 1.3.6.1.2.1.2.2.1.1
-- 1.3.6.1.2.1.2.2.1.1
-- 1.3.6.1.2.1.2.2.1.1
-- 1.3.6.1.2.1.2.2.1.1
-- 1.3.6.1.2.1.2.2.1.1
-- 1.3.6.1.2.1.2.2.1.1
		-- 1.3.6.1.2.1.2.2.1.1
		ifIndex OBJECT-TYPE
			SYNTAX InterfaceIndex
			MAX-ACCESS read-only
			STATUS current
			DESCRIPTION
				"A unique value, greater than zero, for each interface.  It
				is recommended that values are assigned contiguously
				starting from 1.  The value for each interface sub-layer
				must remain constant at least from one re-initialization of
				the entity's network management system to the next re-
				initialization."
			::= { ifEntry 1 }

		
--        1.3.6.1.2.1.2.2.1.2
-- 1.3.6.1.2.1.2.2.1.2
-- 1.3.6.1.2.1.2.2.1.2
-- 1.3.6.1.2.1.2.2.1.2
-- 1.3.6.1.2.1.2.2.1.2
-- 1.3.6.1.2.1.2.2.1.2
-- 1.3.6.1.2.1.2.2.1.2
		-- 1.3.6.1.2.1.2.2.1.2
		ifDescr OBJECT-TYPE
			SYNTAX DisplayString
			MAX-ACCESS read-only
			STATUS current
			DESCRIPTION
				"A textual string containing information about the
				interface.  This string should include the name of the
				manufacturer, the product name and the version of the
				interface hardware/software."
			::= { ifEntry 2 }

		
--        1.3.6.1.2.1.2.2.1.3
-- 1.3.6.1.2.1.2.2.1.3
-- 1.3.6.1.2.1.2.2.1.3
-- 1.3.6.1.2.1.2.2.1.3
-- 1.3.6.1.2.1.2.2.1.3
-- 1.3.6.1.2.1.2.2.1.3
-- 1.3.6.1.2.1.2.2.1.3
		-- 1.3.6.1.2.1.2.2.1.3
		ifType OBJECT-TYPE
			SYNTAX IANAifType
			MAX-ACCESS read-only
			STATUS current
			DESCRIPTION
				"The type of interface.  Additional values for ifType are
				assigned by the Internet Assigned Numbers Authority (IANA),
				through updating the syntax of the IANAifType textual
				convention."
			::= { ifEntry 3 }

		
--        1.3.6.1.2.1.2.2.1.4
-- 1.3.6.1.2.1.2.2.1.4
-- 1.3.6.1.2.1.2.2.1.4
-- 1.3.6.1.2.1.2.2.1.4
-- 1.3.6.1.2.1.2.2.1.4
-- 1.3.6.1.2.1.2.2.1.4
-- 1.3.6.1.2.1.2.2.1.4
		-- 1.3.6.1.2.1.2.2.1.4
		ifMtu OBJECT-TYPE
			SYNTAX Integer32
			MAX-ACCESS read-only
			STATUS current
			DESCRIPTION
				"The size of the largest packet which can be sent/received
				on the interface, specified in octets.  For interfaces that
				are used for transmitting network datagrams, this is the
				size of the largest network datagram that can be sent on the
				interface."
			::= { ifEntry 4 }

		
--        1.3.6.1.2.1.2.2.1.5
-- 1.3.6.1.2.1.2.2.1.5
-- 1.3.6.1.2.1.2.2.1.5
-- 1.3.6.1.2.1.2.2.1.5
-- 1.3.6.1.2.1.2.2.1.5
-- 1.3.6.1.2.1.2.2.1.5
-- 1.3.6.1.2.1.2.2.1.5
		-- 1.3.6.1.2.1.2.2.1.5
		ifSpeed OBJECT-TYPE
			SYNTAX Gauge32
			MAX-ACCESS read-only
			STATUS current
			DESCRIPTION
				"An estimate of the interface's current bandwidth in bits
				per second.  For interfaces which do not vary in bandwidth
				or for those where no accurate estimation can be made, this
				object should contain the nominal bandwidth.  If the
				bandwidth of the interface is greater than the maximum value
				reportable by this object then this object should report its
				maximum value (4,294,967,295) and ifHighSpeed must be used
				to report the interace's speed.  For a sub-layer which has
				no concept of bandwidth, this object should be zero."
			::= { ifEntry 5 }

		
--        1.3.6.1.2.1.2.2.1.6
-- 1.3.6.1.2.1.2.2.1.6
-- 1.3.6.1.2.1.2.2.1.6
-- 1.3.6.1.2.1.2.2.1.6
-- 1.3.6.1.2.1.2.2.1.6
-- 1.3.6.1.2.1.2.2.1.6
-- 1.3.6.1.2.1.2.2.1.6
		-- 1.3.6.1.2.1.2.2.1.6
		ifPhysAddress OBJECT-TYPE
			SYNTAX PhysAddress
			MAX-ACCESS read-only
			STATUS current
			DESCRIPTION
				"The interface's address at its protocol sub-layer.  For
				example, for an 802.x interface, this object normally
				contains a MAC address.  The interface's media-specific MIB
				must define the bit and byte ordering and the format of the
				value of this object.  For interfaces which do not have such
				an address (e.g., a serial line), this object should contain
				an octet string of zero length."
			::= { ifEntry 6 }

		
--         ready to pass packets
-- in some test mode
-- 1.3.6.1.2.1.2.2.1.7
-- 1.3.6.1.2.1.2.2.1.7
-- 1.3.6.1.2.1.2.2.1.7
-- 1.3.6.1.2.1.2.2.1.7
-- 1.3.6.1.2.1.2.2.1.7
-- 1.3.6.1.2.1.2.2.1.7
-- 1.3.6.1.2.1.2.2.1.7
		-- 1.3.6.1.2.1.2.2.1.7
		ifAdminStatus OBJECT-TYPE
			SYNTAX INTEGER
				{
				up(1),
				down(2),
				testing(3)
				}
			MAX-ACCESS read-write
			STATUS current
			DESCRIPTION
				"The desired state of the interface.  The testing(3) state
				indicates that no operational packets can be passed.  When a
				managed system initializes, all interfaces start with
				ifAdminStatus in the down(2) state.  As a result of either
				explicit management action or per configuration information
				retained by the managed system, ifAdminStatus is then
				changed to either the up(1) or testing(3) states (or remains
				in the down(2) state)."
			::= { ifEntry 7 }

		
--         ready to pass packets
-- in some test mode
-- status can not be determined
-- for some reason.
-- some component is missing
-- down due to state of
-- lower-layer interface(s)
-- 1.3.6.1.2.1.2.2.1.8
-- 1.3.6.1.2.1.2.2.1.8
-- 1.3.6.1.2.1.2.2.1.8
-- 1.3.6.1.2.1.2.2.1.8
-- 1.3.6.1.2.1.2.2.1.8
-- 1.3.6.1.2.1.2.2.1.8
-- 1.3.6.1.2.1.2.2.1.8
		-- 1.3.6.1.2.1.2.2.1.8
		ifOperStatus OBJECT-TYPE
			SYNTAX INTEGER
				{
				up(1),
				down(2),
				testing(3),
				unknown(4),
				dormant(5),
				notPresent(6),
				lowerLayerDown(7)
				}
			MAX-ACCESS read-only
			STATUS current
			DESCRIPTION
				"The current operational state of the interface.  The
				testing(3) state indicates that no operational packets can
				be passed.  If ifAdminStatus is down(2) then ifOperStatus
				should be down(2).  If ifAdminStatus is changed to up(1)
				then ifOperStatus should change to up(1) if the interface is
				ready to transmit and receive network traffic; it should
				change to dormant(5) if the interface is waiting for
				external actions (such as a serial line waiting for an
				incoming connection); it should remain in the down(2) state
				if and only if there is a fault that prevents it from going
				to the up(1) state; it should remain in the notPresent(6)
				state if the interface has missing (typically, hardware)
				components."
			::= { ifEntry 8 }

		
--        1.3.6.1.2.1.2.2.1.9
-- 1.3.6.1.2.1.2.2.1.9
-- 1.3.6.1.2.1.2.2.1.9
-- 1.3.6.1.2.1.2.2.1.9
-- 1.3.6.1.2.1.2.2.1.9
-- 1.3.6.1.2.1.2.2.1.9
-- 1.3.6.1.2.1.2.2.1.9
		-- 1.3.6.1.2.1.2.2.1.9
		ifLastChange OBJECT-TYPE
			SYNTAX TimeTicks
			MAX-ACCESS read-only
			STATUS current
			DESCRIPTION
				"The value of sysUpTime at the time the interface entered
				its current operational state.  If the current state was
				entered prior to the last re-initialization of the local
				network management subsystem, then this object contains a
				zero value."
			::= { ifEntry 9 }

		
--        1.3.6.1.2.1.2.2.1.10
-- 1.3.6.1.2.1.2.2.1.10
-- 1.3.6.1.2.1.2.2.1.10
-- 1.3.6.1.2.1.2.2.1.10
-- 1.3.6.1.2.1.2.2.1.10
-- 1.3.6.1.2.1.2.2.1.10
-- 1.3.6.1.2.1.2.2.1.10
		-- 1.3.6.1.2.1.2.2.1.10
		ifInOctets OBJECT-TYPE
			SYNTAX Counter32
			MAX-ACCESS read-only
			STATUS current
			DESCRIPTION
				"The total number of octets received on the interface,
				
				
				including framing characters.
				
				Discontinuities in the value of this counter can occur at
				re-initialization of the management system, and at other
				times as indicated by the value of
				ifCounterDiscontinuityTime."
			::= { ifEntry 10 }

		
--        1.3.6.1.2.1.2.2.1.11
-- 1.3.6.1.2.1.2.2.1.11
-- 1.3.6.1.2.1.2.2.1.11
-- 1.3.6.1.2.1.2.2.1.11
-- 1.3.6.1.2.1.2.2.1.11
-- 1.3.6.1.2.1.2.2.1.11
-- 1.3.6.1.2.1.2.2.1.11
		-- 1.3.6.1.2.1.2.2.1.11
		ifInUcastPkts OBJECT-TYPE
			SYNTAX Counter32
			MAX-ACCESS read-only
			STATUS current
			DESCRIPTION
				"The number of packets, delivered by this sub-layer to a
				higher (sub-)layer, which were not addressed to a multicast
				or broadcast address at this sub-layer.
				
				Discontinuities in the value of this counter can occur at
				re-initialization of the management system, and at other
				times as indicated by the value of
				ifCounterDiscontinuityTime."
			::= { ifEntry 11 }

		
--        1.3.6.1.2.1.2.2.1.12
-- 1.3.6.1.2.1.2.2.1.12
-- 1.3.6.1.2.1.2.2.1.12
-- 1.3.6.1.2.1.2.2.1.12
-- 1.3.6.1.2.1.2.2.1.12
-- 1.3.6.1.2.1.2.2.1.12
-- 1.3.6.1.2.1.2.2.1.12
		-- 1.3.6.1.2.1.2.2.1.12
		ifInNUcastPkts OBJECT-TYPE
			SYNTAX Counter32
			MAX-ACCESS read-only
			STATUS deprecated
			DESCRIPTION
				"The number of packets, delivered by this sub-layer to a
				higher (sub-)layer, which were addressed to a multicast or
				broadcast address at this sub-layer.
				
				Discontinuities in the value of this counter can occur at
				re-initialization of the management system, and at other
				times as indicated by the value of
				ifCounterDiscontinuityTime.
				
				This object is deprecated in favour of ifInMulticastPkts and
				ifInBroadcastPkts."
			::= { ifEntry 12 }

		
--        1.3.6.1.2.1.2.2.1.13
-- 1.3.6.1.2.1.2.2.1.13
-- 1.3.6.1.2.1.2.2.1.13
-- 1.3.6.1.2.1.2.2.1.13
-- 1.3.6.1.2.1.2.2.1.13
-- 1.3.6.1.2.1.2.2.1.13
-- 1.3.6.1.2.1.2.2.1.13
		-- 1.3.6.1.2.1.2.2.1.13
		ifInDiscards OBJECT-TYPE
			SYNTAX Counter32
			MAX-ACCESS read-only
			STATUS current
			DESCRIPTION
				"The number of inbound packets which were chosen to be
				discarded even though no errors had been detected to prevent
				
				
				their being deliverable to a higher-layer protocol.  One
				possible reason for discarding such a packet could be to
				free up buffer space.
				
				Discontinuities in the value of this counter can occur at
				re-initialization of the management system, and at other
				times as indicated by the value of
				ifCounterDiscontinuityTime."
			::= { ifEntry 13 }

		
--        1.3.6.1.2.1.2.2.1.14
-- 1.3.6.1.2.1.2.2.1.14
-- 1.3.6.1.2.1.2.2.1.14
-- 1.3.6.1.2.1.2.2.1.14
-- 1.3.6.1.2.1.2.2.1.14
-- 1.3.6.1.2.1.2.2.1.14
-- 1.3.6.1.2.1.2.2.1.14
		-- 1.3.6.1.2.1.2.2.1.14
		ifInErrors OBJECT-TYPE
			SYNTAX Counter32
			MAX-ACCESS read-only
			STATUS current
			DESCRIPTION
				"For packet-oriented interfaces, the number of inbound
				packets that contained errors preventing them from being
				deliverable to a higher-layer protocol.  For character-
				oriented or fixed-length interfaces, the number of inbound
				transmission units that contained errors preventing them
				from being deliverable to a higher-layer protocol.
				
				Discontinuities in the value of this counter can occur at
				re-initialization of the management system, and at other
				times as indicated by the value of
				ifCounterDiscontinuityTime."
			::= { ifEntry 14 }

		
--        1.3.6.1.2.1.2.2.1.15
-- 1.3.6.1.2.1.2.2.1.15
-- 1.3.6.1.2.1.2.2.1.15
-- 1.3.6.1.2.1.2.2.1.15
-- 1.3.6.1.2.1.2.2.1.15
-- 1.3.6.1.2.1.2.2.1.15
-- 1.3.6.1.2.1.2.2.1.15
		-- 1.3.6.1.2.1.2.2.1.15
		ifInUnknownProtos OBJECT-TYPE
			SYNTAX Counter32
			MAX-ACCESS read-only
			STATUS current
			DESCRIPTION
				"For packet-oriented interfaces, the number of packets
				received via the interface which were discarded because of
				an unknown or unsupported protocol.  For character-oriented
				or fixed-length interfaces that support protocol
				multiplexing the number of transmission units received via
				the interface which were discarded because of an unknown or
				unsupported protocol.  For any interface that does not
				support protocol multiplexing, this counter will always be
				0.
				
				Discontinuities in the value of this counter can occur at
				re-initialization of the management system, and at other
				times as indicated by the value of
				ifCounterDiscontinuityTime."
			::= { ifEntry 15 }

		
--        1.3.6.1.2.1.2.2.1.16
-- 1.3.6.1.2.1.2.2.1.16
-- 1.3.6.1.2.1.2.2.1.16
-- 1.3.6.1.2.1.2.2.1.16
-- 1.3.6.1.2.1.2.2.1.16
-- 1.3.6.1.2.1.2.2.1.16
-- 1.3.6.1.2.1.2.2.1.16
		-- 1.3.6.1.2.1.2.2.1.16
		ifOutOctets OBJECT-TYPE
			SYNTAX Counter32
			MAX-ACCESS read-only
			STATUS current
			DESCRIPTION
				"The total number of octets transmitted out of the
				interface, including framing characters.
				
				Discontinuities in the value of this counter can occur at
				re-initialization of the management system, and at other
				times as indicated by the value of
				ifCounterDiscontinuityTime."
			::= { ifEntry 16 }

		
--        1.3.6.1.2.1.2.2.1.17
-- 1.3.6.1.2.1.2.2.1.17
-- 1.3.6.1.2.1.2.2.1.17
-- 1.3.6.1.2.1.2.2.1.17
-- 1.3.6.1.2.1.2.2.1.17
-- 1.3.6.1.2.1.2.2.1.17
-- 1.3.6.1.2.1.2.2.1.17
		-- 1.3.6.1.2.1.2.2.1.17
		ifOutUcastPkts OBJECT-TYPE
			SYNTAX Counter32
			MAX-ACCESS read-only
			STATUS current
			DESCRIPTION
				"The total number of packets that higher-level protocols
				requested be transmitted, and which were not addressed to a
				multicast or broadcast address at this sub-layer, including
				those that were discarded or not sent.
				
				Discontinuities in the value of this counter can occur at
				re-initialization of the management system, and at other
				times as indicated by the value of
				ifCounterDiscontinuityTime."
			::= { ifEntry 17 }

		
--        1.3.6.1.2.1.2.2.1.18
-- 1.3.6.1.2.1.2.2.1.18
-- 1.3.6.1.2.1.2.2.1.18
-- 1.3.6.1.2.1.2.2.1.18
-- 1.3.6.1.2.1.2.2.1.18
-- 1.3.6.1.2.1.2.2.1.18
-- 1.3.6.1.2.1.2.2.1.18
		-- 1.3.6.1.2.1.2.2.1.18
		ifOutNUcastPkts OBJECT-TYPE
			SYNTAX Counter32
			MAX-ACCESS read-only
			STATUS deprecated
			DESCRIPTION
				"The total number of packets that higher-level protocols
				requested be transmitted, and which were addressed to a
				multicast or broadcast address at this sub-layer, including
				those that were discarded or not sent.
				
				Discontinuities in the value of this counter can occur at
				re-initialization of the management system, and at other
				times as indicated by the value of
				ifCounterDiscontinuityTime.
				
				This object is deprecated in favour of ifOutMulticastPkts
				and ifOutBroadcastPkts."
			::= { ifEntry 18 }

		
--        1.3.6.1.2.1.2.2.1.19
-- 1.3.6.1.2.1.2.2.1.19
-- 1.3.6.1.2.1.2.2.1.19
-- 1.3.6.1.2.1.2.2.1.19
-- 1.3.6.1.2.1.2.2.1.19
-- 1.3.6.1.2.1.2.2.1.19
-- 1.3.6.1.2.1.2.2.1.19
		-- 1.3.6.1.2.1.2.2.1.19
		ifOutDiscards OBJECT-TYPE
			SYNTAX Counter32
			MAX-ACCESS read-only
			STATUS current
			DESCRIPTION
				"The number of outbound packets which were chosen to be
				discarded even though no errors had been detected to prevent
				their being transmitted.  One possible reason for discarding
				such a packet could be to free up buffer space.
				
				Discontinuities in the value of this counter can occur at
				re-initialization of the management system, and at other
				times as indicated by the value of
				ifCounterDiscontinuityTime."
			::= { ifEntry 19 }

		
--        1.3.6.1.2.1.2.2.1.20
-- 1.3.6.1.2.1.2.2.1.20
-- 1.3.6.1.2.1.2.2.1.20
-- 1.3.6.1.2.1.2.2.1.20
-- 1.3.6.1.2.1.2.2.1.20
-- 1.3.6.1.2.1.2.2.1.20
-- 1.3.6.1.2.1.2.2.1.20
		-- 1.3.6.1.2.1.2.2.1.20
		ifOutErrors OBJECT-TYPE
			SYNTAX Counter32
			MAX-ACCESS read-only
			STATUS current
			DESCRIPTION
				"For packet-oriented interfaces, the number of outbound
				packets that could not be transmitted because of errors.
				For character-oriented or fixed-length interfaces, the
				number of outbound transmission units that could not be
				transmitted because of errors.
				
				Discontinuities in the value of this counter can occur at
				re-initialization of the management system, and at other
				times as indicated by the value of
				ifCounterDiscontinuityTime."
			::= { ifEntry 20 }

		
--        1.3.6.1.2.1.2.2.1.21
-- 1.3.6.1.2.1.2.2.1.21
-- 1.3.6.1.2.1.2.2.1.21
-- 1.3.6.1.2.1.2.2.1.21
-- 1.3.6.1.2.1.2.2.1.21
-- 1.3.6.1.2.1.2.2.1.21
-- 1.3.6.1.2.1.2.2.1.21
		-- 1.3.6.1.2.1.2.2.1.21
		ifOutQLen OBJECT-TYPE
			SYNTAX Gauge32
			MAX-ACCESS read-only
			STATUS deprecated
			DESCRIPTION
				"The length of the output packet queue (in packets)."
			::= { ifEntry 21 }

		
--        1.3.6.1.2.1.2.2.1.22
-- 1.3.6.1.2.1.2.2.1.22
-- 1.3.6.1.2.1.2.2.1.22
-- 1.3.6.1.2.1.2.2.1.22
-- 1.3.6.1.2.1.2.2.1.22
-- 1.3.6.1.2.1.2.2.1.22
-- 1.3.6.1.2.1.2.2.1.22
		-- 1.3.6.1.2.1.2.2.1.22
		ifSpecific OBJECT-TYPE
			SYNTAX OBJECT IDENTIFIER
			MAX-ACCESS read-only
			STATUS deprecated
			DESCRIPTION
				"A reference to MIB definitions specific to the particular
				media being used to realize the interface.  It is
				
				
				recommended that this value point to an instance of a MIB
				object in the media-specific MIB, i.e., that this object
				have the semantics associated with the InstancePointer
				textual convention defined in RFC 2579.  In fact, it is
				recommended that the media-specific MIB specify what value
				ifSpecific should/can take for values of ifType.  If no MIB
				definitions specific to the particular media are available,
				the value should be set to the OBJECT IDENTIFIER { 0 0 }."
			::= { ifEntry 22 }

		
--          the SNMP group
-- 
-- a collection of objects providing basic instrumentation and
-- control of an SNMP entity.
-- 1.3.6.1.2.1.2
-- 1.3.6.1.2.1.3
-- 1.3.6.1.2.1.3
-- 1.3.6.1.2.1.3
-- 1.3.6.1.2.1.3
-- 1.3.6.1.2.1.3
-- 1.3.6.1.2.1.3
-- 1.3.6.1.2.1.3
		-- 1.3.6.1.2.1.3
		snmp OBJECT IDENTIFIER ::= { mib-2 3 }

		
--         1.3.6.1.2.1.2.1
-- 1.3.6.1.2.1.3.1
-- 1.3.6.1.2.1.3.1
-- 1.3.6.1.2.1.3.1
-- 1.3.6.1.2.1.3.1
-- 1.3.6.1.2.1.3.1
-- 1.3.6.1.2.1.3.1
-- 1.3.6.1.2.1.3.1
		-- 1.3.6.1.2.1.3.1
		snmpInPkts OBJECT-TYPE
			SYNTAX Counter32
			MAX-ACCESS read-only
			STATUS current
			DESCRIPTION
				"The total number of messages delivered to the SNMP
				entity from the transport service."
			::= { snmp 1 }

		
--          definitions in RFC 1213 made obsolete by the inclusion of a
-- subset of the snmp group in this MIB
-- 1.3.6.1.2.1.2.2
-- 1.3.6.1.2.1.3.2
-- 1.3.6.1.2.1.3.2
-- 1.3.6.1.2.1.3.2
-- 1.3.6.1.2.1.3.2
-- 1.3.6.1.2.1.3.2
-- 1.3.6.1.2.1.3.2
-- 1.3.6.1.2.1.3.2
		-- 1.3.6.1.2.1.3.2
		snmpOutPkts OBJECT-TYPE
			SYNTAX Counter32
			MAX-ACCESS read-only
			STATUS obsolete
			DESCRIPTION
				"The total number of SNMP Messages which were
				passed from the SNMP protocol entity to the
				transport service."
			::= { snmp 2 }

		
--         1.3.6.1.2.1.2.3
-- 1.3.6.1.2.1.3.3
-- 1.3.6.1.2.1.3.3
-- 1.3.6.1.2.1.3.3
-- 1.3.6.1.2.1.3.3
-- 1.3.6.1.2.1.3.3
-- 1.3.6.1.2.1.3.3
-- 1.3.6.1.2.1.3.3
		-- 1.3.6.1.2.1.3.3
		snmpInBadVersions OBJECT-TYPE
			SYNTAX Counter32
			MAX-ACCESS read-only
			STATUS current
			DESCRIPTION
				"The total number of SNMP messages which were delivered
				to the SNMP entity and were for an unsupported SNMP
				version."
			::= { snmp 3 }

		
--         1.3.6.1.2.1.2.4
-- 1.3.6.1.2.1.3.4
-- 1.3.6.1.2.1.3.4
-- 1.3.6.1.2.1.3.4
-- 1.3.6.1.2.1.3.4
-- 1.3.6.1.2.1.3.4
-- 1.3.6.1.2.1.3.4
-- 1.3.6.1.2.1.3.4
		-- 1.3.6.1.2.1.3.4
		snmpInBadCommunityNames OBJECT-TYPE
			SYNTAX Counter32
			MAX-ACCESS read-only
			STATUS current
			DESCRIPTION
				"The total number of community-based SNMP messages (for
				example,  SNMPv1) delivered to the SNMP entity which
				used an SNMP community name not known to said entity.
				Also, implementations which authenticate community-based
				SNMP messages using check(s) in addition to matching
				the community name (for example, by also checking
				whether the message originated from a transport address
				allowed to use a specified community name) MAY include
				in this value the number of messages which failed the
				additional check(s).  It is strongly RECOMMENDED that
				
				
				the documentation for any security model which is used
				to authenticate community-based SNMP messages specify
				the precise conditions that contribute to this value."
			::= { snmp 4 }

		
--         1.3.6.1.2.1.2.5
-- 1.3.6.1.2.1.3.5
-- 1.3.6.1.2.1.3.5
-- 1.3.6.1.2.1.3.5
-- 1.3.6.1.2.1.3.5
-- 1.3.6.1.2.1.3.5
-- 1.3.6.1.2.1.3.5
-- 1.3.6.1.2.1.3.5
		-- 1.3.6.1.2.1.3.5
		snmpInBadCommunityUses OBJECT-TYPE
			SYNTAX Counter32
			MAX-ACCESS read-only
			STATUS current
			DESCRIPTION
				"The total number of community-based SNMP messages (for
				example, SNMPv1) delivered to the SNMP entity which
				represented an SNMP operation that was not allowed for
				the SNMP community named in the message.  The precise
				conditions under which this counter is incremented
				(if at all) depend on how the SNMP entity implements
				its access control mechanism and how its applications
				interact with that access control mechanism.  It is
				strongly RECOMMENDED that the documentation for any
				access control mechanism which is used to control access
				to and visibility of MIB instrumentation specify the
				precise conditions that contribute to this value."
			::= { snmp 5 }

		
--         1.3.6.1.2.1.2.6
-- 1.3.6.1.2.1.3.6
-- 1.3.6.1.2.1.3.6
-- 1.3.6.1.2.1.3.6
-- 1.3.6.1.2.1.3.6
-- 1.3.6.1.2.1.3.6
-- 1.3.6.1.2.1.3.6
-- 1.3.6.1.2.1.3.6
		-- 1.3.6.1.2.1.3.6
		snmpInASNParseErrs OBJECT-TYPE
			SYNTAX Counter32
			MAX-ACCESS read-only
			STATUS current
			DESCRIPTION
				"The total number of ASN.1 or BER errors encountered by
				the SNMP entity when decoding received SNMP messages."
			::= { snmp 6 }

		
--          { snmp 7 } is not used
-- 1.3.6.1.2.1.2.8
-- 1.3.6.1.2.1.3.8
-- 1.3.6.1.2.1.3.8
-- 1.3.6.1.2.1.3.8
-- 1.3.6.1.2.1.3.8
-- 1.3.6.1.2.1.3.8
-- 1.3.6.1.2.1.3.8
-- 1.3.6.1.2.1.3.8
		-- 1.3.6.1.2.1.3.8
		snmpInTooBigs OBJECT-TYPE
			SYNTAX Counter32
			MAX-ACCESS read-only
			STATUS obsolete
			DESCRIPTION
				"The total number of SNMP PDUs which were
				delivered to the SNMP protocol entity and for
				which the value of the error-status field was
				`tooBig'."
			::= { snmp 8 }

		
--         1.3.6.1.2.1.2.9
-- 1.3.6.1.2.1.3.9
-- 1.3.6.1.2.1.3.9
-- 1.3.6.1.2.1.3.9
-- 1.3.6.1.2.1.3.9
-- 1.3.6.1.2.1.3.9
-- 1.3.6.1.2.1.3.9
-- 1.3.6.1.2.1.3.9
		-- 1.3.6.1.2.1.3.9
		snmpInNoSuchNames OBJECT-TYPE
			SYNTAX Counter32
			MAX-ACCESS read-only
			STATUS obsolete
			DESCRIPTION
				"The total number of SNMP PDUs which were
				delivered to the SNMP protocol entity and for
				which the value of the error-status field was
				`noSuchName'."
			::= { snmp 9 }

		
--         1.3.6.1.2.1.2.10
-- 1.3.6.1.2.1.3.10
-- 1.3.6.1.2.1.3.10
-- 1.3.6.1.2.1.3.10
-- 1.3.6.1.2.1.3.10
-- 1.3.6.1.2.1.3.10
-- 1.3.6.1.2.1.3.10
-- 1.3.6.1.2.1.3.10
		-- 1.3.6.1.2.1.3.10
		snmpInBadValues OBJECT-TYPE
			SYNTAX Counter32
			MAX-ACCESS read-only
			STATUS obsolete
			DESCRIPTION
				"The total number of SNMP PDUs which were
				delivered to the SNMP protocol entity and for
				which the value of the error-status field was
				`badValue'."
			::= { snmp 10 }

		
--         1.3.6.1.2.1.2.11
-- 1.3.6.1.2.1.3.11
-- 1.3.6.1.2.1.3.11
-- 1.3.6.1.2.1.3.11
-- 1.3.6.1.2.1.3.11
-- 1.3.6.1.2.1.3.11
-- 1.3.6.1.2.1.3.11
-- 1.3.6.1.2.1.3.11
		-- 1.3.6.1.2.1.3.11
		snmpInReadOnlys OBJECT-TYPE
			SYNTAX Counter32
			MAX-ACCESS read-only
			STATUS obsolete
			DESCRIPTION
				"The total number valid SNMP PDUs which were delivered
				to the SNMP protocol entity and for which the value
				of the error-status field was `readOnly'.  It should
				be noted that it is a protocol error to generate an
				SNMP PDU which contains the value `readOnly' in the
				error-status field, as such this object is provided
				as a means of detecting incorrect implementations of
				the SNMP."
			::= { snmp 11 }

		
--         1.3.6.1.2.1.2.12
-- 1.3.6.1.2.1.3.12
-- 1.3.6.1.2.1.3.12
-- 1.3.6.1.2.1.3.12
-- 1.3.6.1.2.1.3.12
-- 1.3.6.1.2.1.3.12
-- 1.3.6.1.2.1.3.12
-- 1.3.6.1.2.1.3.12
		-- 1.3.6.1.2.1.3.12
		snmpInGenErrs OBJECT-TYPE
			SYNTAX Counter32
			MAX-ACCESS read-only
			STATUS obsolete
			DESCRIPTION
				"The total number of SNMP PDUs which were delivered
				to the SNMP protocol entity and for which the value
				of the error-status field was `genErr'."
			::= { snmp 12 }

		
--         1.3.6.1.2.1.2.13
-- 1.3.6.1.2.1.3.13
-- 1.3.6.1.2.1.3.13
-- 1.3.6.1.2.1.3.13
-- 1.3.6.1.2.1.3.13
-- 1.3.6.1.2.1.3.13
-- 1.3.6.1.2.1.3.13
-- 1.3.6.1.2.1.3.13
		-- 1.3.6.1.2.1.3.13
		snmpInTotalReqVars OBJECT-TYPE
			SYNTAX Counter32
			MAX-ACCESS read-only
			STATUS obsolete
			DESCRIPTION
				"The total number of MIB objects which have been
				retrieved successfully by the SNMP protocol entity
				as the result of receiving valid SNMP Get-Request
				and Get-Next PDUs."
			::= { snmp 13 }

		
--         1.3.6.1.2.1.2.14
-- 1.3.6.1.2.1.3.14
-- 1.3.6.1.2.1.3.14
-- 1.3.6.1.2.1.3.14
-- 1.3.6.1.2.1.3.14
-- 1.3.6.1.2.1.3.14
-- 1.3.6.1.2.1.3.14
-- 1.3.6.1.2.1.3.14
		-- 1.3.6.1.2.1.3.14
		snmpInTotalSetVars OBJECT-TYPE
			SYNTAX Counter32
			MAX-ACCESS read-only
			STATUS obsolete
			DESCRIPTION
				"The total number of MIB objects which have been
				altered successfully by the SNMP protocol entity as
				the result of receiving valid SNMP Set-Request PDUs."
			::= { snmp 14 }

		
--         1.3.6.1.2.1.2.15
-- 1.3.6.1.2.1.3.15
-- 1.3.6.1.2.1.3.15
-- 1.3.6.1.2.1.3.15
-- 1.3.6.1.2.1.3.15
-- 1.3.6.1.2.1.3.15
-- 1.3.6.1.2.1.3.15
-- 1.3.6.1.2.1.3.15
		-- 1.3.6.1.2.1.3.15
		snmpInGetRequests OBJECT-TYPE
			SYNTAX Counter32
			MAX-ACCESS read-only
			STATUS obsolete
			DESCRIPTION
				"The total number of SNMP Get-Request PDUs which
				have been accepted and processed by the SNMP
				protocol entity."
			::= { snmp 15 }

		
--         1.3.6.1.2.1.2.16
-- 1.3.6.1.2.1.3.16
-- 1.3.6.1.2.1.3.16
-- 1.3.6.1.2.1.3.16
-- 1.3.6.1.2.1.3.16
-- 1.3.6.1.2.1.3.16
-- 1.3.6.1.2.1.3.16
-- 1.3.6.1.2.1.3.16
		-- 1.3.6.1.2.1.3.16
		snmpInGetNexts OBJECT-TYPE
			SYNTAX Counter32
			MAX-ACCESS read-only
			STATUS obsolete
			DESCRIPTION
				"The total number of SNMP Get-Next PDUs which have been
				accepted and processed by the SNMP protocol entity."
			::= { snmp 16 }

		
--         1.3.6.1.2.1.2.17
-- 1.3.6.1.2.1.3.17
-- 1.3.6.1.2.1.3.17
-- 1.3.6.1.2.1.3.17
-- 1.3.6.1.2.1.3.17
-- 1.3.6.1.2.1.3.17
-- 1.3.6.1.2.1.3.17
-- 1.3.6.1.2.1.3.17
		-- 1.3.6.1.2.1.3.17
		snmpInSetRequests OBJECT-TYPE
			SYNTAX Counter32
			MAX-ACCESS read-only
			STATUS obsolete
			DESCRIPTION
				"The total number of SNMP Set-Request PDUs which
				have been accepted and processed by the SNMP protocol
				entity."
			::= { snmp 17 }

		
--         1.3.6.1.2.1.2.18
-- 1.3.6.1.2.1.3.18
-- 1.3.6.1.2.1.3.18
-- 1.3.6.1.2.1.3.18
-- 1.3.6.1.2.1.3.18
-- 1.3.6.1.2.1.3.18
-- 1.3.6.1.2.1.3.18
-- 1.3.6.1.2.1.3.18
		-- 1.3.6.1.2.1.3.18
		snmpInGetResponses OBJECT-TYPE
			SYNTAX Counter32
			MAX-ACCESS read-only
			STATUS obsolete
			DESCRIPTION
				"The total number of SNMP Get-Response PDUs which
				have been accepted and processed by the SNMP protocol
				entity."
			::= { snmp 18 }

		
--         1.3.6.1.2.1.2.19
-- 1.3.6.1.2.1.3.19
-- 1.3.6.1.2.1.3.19
-- 1.3.6.1.2.1.3.19
-- 1.3.6.1.2.1.3.19
-- 1.3.6.1.2.1.3.19
-- 1.3.6.1.2.1.3.19
-- 1.3.6.1.2.1.3.19
		-- 1.3.6.1.2.1.3.19
		snmpInTraps OBJECT-TYPE
			SYNTAX Counter32
			MAX-ACCESS read-only
			STATUS obsolete
			DESCRIPTION
				"The total number of SNMP Trap PDUs which have been
				accepted and processed by the SNMP protocol entity."
			::= { snmp 19 }

		
--         1.3.6.1.2.1.2.20
-- 1.3.6.1.2.1.3.20
-- 1.3.6.1.2.1.3.20
-- 1.3.6.1.2.1.3.20
-- 1.3.6.1.2.1.3.20
-- 1.3.6.1.2.1.3.20
-- 1.3.6.1.2.1.3.20
-- 1.3.6.1.2.1.3.20
		-- 1.3.6.1.2.1.3.20
		snmpOutTooBigs OBJECT-TYPE
			SYNTAX Counter32
			MAX-ACCESS read-only
			STATUS obsolete
			DESCRIPTION
				"The total number of SNMP PDUs which were generated
				by the SNMP protocol entity and for which the value
				of the error-status field was `tooBig.'"
			::= { snmp 20 }

		
--         1.3.6.1.2.1.2.21
-- 1.3.6.1.2.1.3.21
-- 1.3.6.1.2.1.3.21
-- 1.3.6.1.2.1.3.21
-- 1.3.6.1.2.1.3.21
-- 1.3.6.1.2.1.3.21
-- 1.3.6.1.2.1.3.21
-- 1.3.6.1.2.1.3.21
		-- 1.3.6.1.2.1.3.21
		snmpOutNoSuchNames OBJECT-TYPE
			SYNTAX Counter32
			MAX-ACCESS read-only
			STATUS obsolete
			DESCRIPTION
				"The total number of SNMP PDUs which were generated
				by the SNMP protocol entity and for which the value
				of the error-status was `noSuchName'."
			::= { snmp 21 }

		
--         1.3.6.1.2.1.2.22
-- 1.3.6.1.2.1.3.22
-- 1.3.6.1.2.1.3.22
-- 1.3.6.1.2.1.3.22
-- 1.3.6.1.2.1.3.22
-- 1.3.6.1.2.1.3.22
-- 1.3.6.1.2.1.3.22
-- 1.3.6.1.2.1.3.22
		-- 1.3.6.1.2.1.3.22
		snmpOutBadValues OBJECT-TYPE
			SYNTAX Counter32
			MAX-ACCESS read-only
			STATUS obsolete
			DESCRIPTION
				"The total number of SNMP PDUs which were generated
				by the SNMP protocol entity and for which the value
				of the error-status field was `badValue'."
			::= { snmp 22 }

		
--          { snmp 23 } is not used
-- 1.3.6.1.2.1.2.24
-- 1.3.6.1.2.1.3.24
-- 1.3.6.1.2.1.3.24
-- 1.3.6.1.2.1.3.24
-- 1.3.6.1.2.1.3.24
-- 1.3.6.1.2.1.3.24
-- 1.3.6.1.2.1.3.24
-- 1.3.6.1.2.1.3.24
		-- 1.3.6.1.2.1.3.24
		snmpOutGenErrs OBJECT-TYPE
			SYNTAX Counter32
			MAX-ACCESS read-only
			STATUS obsolete
			DESCRIPTION
				"The total number of SNMP PDUs which were generated
				by the SNMP protocol entity and for which the value
				of the error-status field was `genErr'."
			::= { snmp 24 }

		
--         1.3.6.1.2.1.2.25
-- 1.3.6.1.2.1.3.25
-- 1.3.6.1.2.1.3.25
-- 1.3.6.1.2.1.3.25
-- 1.3.6.1.2.1.3.25
-- 1.3.6.1.2.1.3.25
-- 1.3.6.1.2.1.3.25
-- 1.3.6.1.2.1.3.25
		-- 1.3.6.1.2.1.3.25
		snmpOutGetRequests OBJECT-TYPE
			SYNTAX Counter32
			MAX-ACCESS read-only
			STATUS obsolete
			DESCRIPTION
				"The total number of SNMP Get-Request PDUs which
				have been generated by the SNMP protocol entity."
			::= { snmp 25 }

		
--         1.3.6.1.2.1.2.26
-- 1.3.6.1.2.1.3.26
-- 1.3.6.1.2.1.3.26
-- 1.3.6.1.2.1.3.26
-- 1.3.6.1.2.1.3.26
-- 1.3.6.1.2.1.3.26
-- 1.3.6.1.2.1.3.26
-- 1.3.6.1.2.1.3.26
		-- 1.3.6.1.2.1.3.26
		snmpOutGetNexts OBJECT-TYPE
			SYNTAX Counter32
			MAX-ACCESS read-only
			STATUS obsolete
			DESCRIPTION
				"The total number of SNMP Get-Next PDUs which have
				been generated by the SNMP protocol entity."
			::= { snmp 26 }

		
--         1.3.6.1.2.1.2.27
-- 1.3.6.1.2.1.3.27
-- 1.3.6.1.2.1.3.27
-- 1.3.6.1.2.1.3.27
-- 1.3.6.1.2.1.3.27
-- 1.3.6.1.2.1.3.27
-- 1.3.6.1.2.1.3.27
-- 1.3.6.1.2.1.3.27
		-- 1.3.6.1.2.1.3.27
		snmpOutSetRequests OBJECT-TYPE
			SYNTAX Counter32
			MAX-ACCESS read-only
			STATUS obsolete
			DESCRIPTION
				"The total number of SNMP Set-Request PDUs which
				have been generated by the SNMP protocol entity."
			::= { snmp 27 }

		
--         1.3.6.1.2.1.2.28
-- 1.3.6.1.2.1.3.28
-- 1.3.6.1.2.1.3.28
-- 1.3.6.1.2.1.3.28
-- 1.3.6.1.2.1.3.28
-- 1.3.6.1.2.1.3.28
-- 1.3.6.1.2.1.3.28
-- 1.3.6.1.2.1.3.28
		-- 1.3.6.1.2.1.3.28
		snmpOutGetResponses OBJECT-TYPE
			SYNTAX Counter32
			MAX-ACCESS read-only
			STATUS obsolete
			DESCRIPTION
				"The total number of SNMP Get-Response PDUs which
				have been generated by the SNMP protocol entity."
			::= { snmp 28 }

		
--         1.3.6.1.2.1.2.29
-- 1.3.6.1.2.1.3.29
-- 1.3.6.1.2.1.3.29
-- 1.3.6.1.2.1.3.29
-- 1.3.6.1.2.1.3.29
-- 1.3.6.1.2.1.3.29
-- 1.3.6.1.2.1.3.29
-- 1.3.6.1.2.1.3.29
		-- 1.3.6.1.2.1.3.29
		snmpOutTraps OBJECT-TYPE
			SYNTAX Counter32
			MAX-ACCESS read-only
			STATUS obsolete
			DESCRIPTION
				"The total number of SNMP Trap PDUs which have
				been generated by the SNMP protocol entity."
			::= { snmp 29 }

		
--         1.3.6.1.2.1.2.30
-- 1.3.6.1.2.1.3.30
-- 1.3.6.1.2.1.3.30
-- 1.3.6.1.2.1.3.30
-- 1.3.6.1.2.1.3.30
-- 1.3.6.1.2.1.3.30
-- 1.3.6.1.2.1.3.30
-- 1.3.6.1.2.1.3.30
		-- 1.3.6.1.2.1.3.30
		snmpEnableAuthenTraps OBJECT-TYPE
			SYNTAX INTEGER
				{
				enabled(1),
				disabled(2)
				}
			MAX-ACCESS read-write
			STATUS current
			DESCRIPTION
				"Indicates whether the SNMP entity is permitted to
				generate authenticationFailure traps.  The value of this
				object overrides any configuration information; as such,
				it provides a means whereby all authenticationFailure
				traps may be disabled.
				
				Note that it is strongly recommended that this object
				be stored in non-volatile memory so that it remains
				constant across re-initializations of the network
				management system."
			::= { snmp 30 }

		
--         1.3.6.1.2.1.2.31
-- 1.3.6.1.2.1.3.31
-- 1.3.6.1.2.1.3.31
-- 1.3.6.1.2.1.3.31
-- 1.3.6.1.2.1.3.31
-- 1.3.6.1.2.1.3.31
-- 1.3.6.1.2.1.3.31
-- 1.3.6.1.2.1.3.31
		-- 1.3.6.1.2.1.3.31
		snmpSilentDrops OBJECT-TYPE
			SYNTAX Counter32
			MAX-ACCESS read-only
			STATUS current
			DESCRIPTION
				"The total number of Confirmed Class PDUs (such as
				GetRequest-PDUs, GetNextRequest-PDUs,
				GetBulkRequest-PDUs, SetRequest-PDUs, and
				InformRequest-PDUs) delivered to the SNMP entity which
				were silently dropped because the size of a reply
				containing an alternate Response Class PDU (such as a
				Response-PDU) with an empty variable-bindings field
				was greater than either a local constraint or the
				maximum message size associated with the originator of
				the request."
			::= { snmp 31 }

		
--         1.3.6.1.2.1.2.32
-- 1.3.6.1.2.1.3.32
-- 1.3.6.1.2.1.3.32
-- 1.3.6.1.2.1.3.32
-- 1.3.6.1.2.1.3.32
-- 1.3.6.1.2.1.3.32
-- 1.3.6.1.2.1.3.32
-- 1.3.6.1.2.1.3.32
		-- 1.3.6.1.2.1.3.32
		snmpProxyDrops OBJECT-TYPE
			SYNTAX Counter32
			MAX-ACCESS read-only
			STATUS current
			DESCRIPTION
				"The total number of Confirmed Class PDUs
				(such as GetRequest-PDUs, GetNextRequest-PDUs,
				GetBulkRequest-PDUs, SetRequest-PDUs, and
				InformRequest-PDUs) delivered to the SNMP entity which
				were silently dropped because the transmission of
				the (possibly translated) message to a proxy target
				failed in a manner (other than a time-out) such that
				no Response Class PDU (such as a Response-PDU) could
				be returned."
			::= { snmp 32 }

		
--          DESCRIPTION
-- "nscrtvRoot定义全国广播电视标准化技术委员会MIB根节点。"
-- 1.3.6.1.4.1.1.1
-- 1.3.6.1.4.1.17409.1
-- 1.3.6.1.4.1.17409.1
-- 1.3.6.1.4.1.17409.1
-- 1.3.6.1.4.1.17409.1
-- 1.3.6.1.4.1.17409.1
-- 1.3.6.1.4.1.17409.1
-- 1.3.6.1.4.1.17409.1
		-- 1.3.6.1.4.1.17409.1
		nscrtvHFCemsTree OBJECT IDENTIFIER ::= { nscrtvRoot 1 }

		
--         1.3.6.1.4.1.1.1.0
-- 1.3.6.1.4.1.17409.1.0
-- 1.3.6.1.4.1.17409.1.0
-- 1.3.6.1.4.1.17409.1.0
-- 1.3.6.1.4.1.17409.1.0
-- 1.3.6.1.4.1.17409.1.0
-- 1.3.6.1.4.1.17409.1.0
-- 1.3.6.1.4.1.17409.1.0
		-- 1.3.6.1.4.1.17409.1.0
		nscrtvHFCemsTreeV2 OBJECT-IDENTITY
			STATUS current
			DESCRIPTION 
				"Root node for the converted TRAP-TYPEs."
			::= { nscrtvHFCemsTree 0 }

		
--          *
-- * hfcColdStart和 hfcWarmStart 陷阱用于替代标准SNMP陷阱coldStart和warmStart，以便
-- * 将应答器物理地址包含在陷阱消息中。
-- * TRAP-TYPE宏由RFC 1215定义。
-- *
-- 1.3.6.1.4.1.1.1.0.0
-- 1.3.6.1.4.1.17409.1.0.0
-- 1.3.6.1.4.1.17409.1.0.0
-- 1.3.6.1.4.1.17409.1.0.0
-- 1.3.6.1.4.1.17409.1.0.0
-- 1.3.6.1.4.1.17409.1.0.0
-- 1.3.6.1.4.1.17409.1.0.0
-- 1.3.6.1.4.1.17409.1.0.0
		-- 1.3.6.1.4.1.17409.1.0.0
		hfcColdStart NOTIFICATION-TYPE
			OBJECTS { commonPhysAddress, commonNELogicalID }
			STATUS current
			DESCRIPTION 
				"hfcColdStart陷阱表示发送方协议实体正重新初始化，并且代理配置或协议实体可能有改变。此陷阱仅在应答器注册成功后发送。"
			::= { nscrtvHFCemsTreeV2 0 }

		
--         1.3.6.1.4.1.1.1.0.1
-- 1.3.6.1.4.1.17409.1.0.1
-- 1.3.6.1.4.1.17409.1.0.1
-- 1.3.6.1.4.1.17409.1.0.1
-- 1.3.6.1.4.1.17409.1.0.1
-- 1.3.6.1.4.1.17409.1.0.1
-- 1.3.6.1.4.1.17409.1.0.1
-- 1.3.6.1.4.1.17409.1.0.1
		-- 1.3.6.1.4.1.17409.1.0.1
		hfcAlarmEvent NOTIFICATION-TYPE
			OBJECTS { commonPhysAddress, commonNELogicalID, alarmLogInformation, alarmText }
			STATUS current
			DESCRIPTION 
				"当检测到告警事件时发送此陷阱消息，是否绑定alarmText变量根据告警参数对象来确定。某些参数的告警只需要绑定前三个变量。"
			::= { nscrtvHFCemsTreeV2 1 }

		
--         1.3.6.1.4.1.1.1.0.2
-- 1.3.6.1.4.1.17409.1.0.2
-- 1.3.6.1.4.1.17409.1.0.2
-- 1.3.6.1.4.1.17409.1.0.2
-- 1.3.6.1.4.1.17409.1.0.2
-- 1.3.6.1.4.1.17409.1.0.2
-- 1.3.6.1.4.1.17409.1.0.2
-- 1.3.6.1.4.1.17409.1.0.2
		-- 1.3.6.1.4.1.17409.1.0.2
		hfcWarmStart NOTIFICATION-TYPE
			OBJECTS { commonPhysAddress, commonNELogicalID }
			STATUS current
			DESCRIPTION 
				"hfcWarmStart陷阱表示发送方协议实体正重新初始化，并且代理配置或协议实体没有任何改变。此陷阱仅在应答器注册完成后发送。"
			::= { nscrtvHFCemsTreeV2 2 }

		
--          DESCRIPTION
-- "nscrtvHFCemsTree定义HFC网络设备管理系统MIB根节点,"
-- "所有HFC网络设备管理系统的MIB均应在该节点下定义。"
-- 1.3.6.1.4.1.1.1.1
-- 1.3.6.1.4.1.17409.1.1
-- 1.3.6.1.4.1.17409.1.1
-- 1.3.6.1.4.1.17409.1.1
-- 1.3.6.1.4.1.17409.1.1
-- 1.3.6.1.4.1.17409.1.1
-- 1.3.6.1.4.1.17409.1.1
-- 1.3.6.1.4.1.17409.1.1
		-- 1.3.6.1.4.1.17409.1.1
		propertyIdent OBJECT IDENTIFIER ::= { nscrtvHFCemsTree 1 }

		
--              DESCRIPTION
-- "线路(Line)MIB的分支节点标识。"
-- "见附录P。"
-- **********************************************************************************************
--                                属性MIB
-- **********************************************************************************************
-- 1.3.6.1.4.1.1.1.1.1
-- 1.3.6.1.4.1.17409.1.1.1
-- 1.3.6.1.4.1.17409.1.1.1
-- 1.3.6.1.4.1.17409.1.1.1
-- 1.3.6.1.4.1.17409.1.1.1
-- 1.3.6.1.4.1.17409.1.1.1
-- 1.3.6.1.4.1.17409.1.1.1
-- 1.3.6.1.4.1.17409.1.1.1
		-- 1.3.6.1.4.1.17409.1.1.1
		analogPropertyTable OBJECT-TYPE
			SYNTAX SEQUENCE OF AnalogPropertyEntry
			MAX-ACCESS not-accessible
			STATUS current
			DESCRIPTION
				"模拟参数属性表。"
			::= { propertyIdent 1 }

		
--         1.3.6.1.4.1.1.1.1.1.1
-- 1.3.6.1.4.1.17409.1.1.1.1
-- 1.3.6.1.4.1.17409.1.1.1.1
-- 1.3.6.1.4.1.17409.1.1.1.1
-- 1.3.6.1.4.1.17409.1.1.1.1
-- 1.3.6.1.4.1.17409.1.1.1.1
-- 1.3.6.1.4.1.17409.1.1.1.1
-- 1.3.6.1.4.1.17409.1.1.1.1
		-- 1.3.6.1.4.1.17409.1.1.1.1
		analogPropertyEntry OBJECT-TYPE
			SYNTAX AnalogPropertyEntry
			MAX-ACCESS not-accessible
			STATUS current
			DESCRIPTION
				"模拟参数属性表目。OID作为表目的索引，其编码方法是'长度＋OID'。OID的前2个成员'1.3'是按'1'和'3'分别编码，而不是普通OID编码方式(0x2B)。"
			INDEX { analogParameterOID }
			::= { analogPropertyTable 1 }

		
		AnalogPropertyEntry ::=
			SEQUENCE { 
				analogParameterOID
					OBJECT IDENTIFIER,
				alarmEnable
					OCTET STRING,
				analogAlarmState
					INTEGER,
				analogAlarmHIHI
					Integer32,
				analogAlarmHI
					Integer32,
				analogAlarmLO
					Integer32,
				analogAlarmLOLO
					Integer32,
				analogAlarmDeadband
					Integer32
			 }

--         1.3.6.1.4.1.1.1.1.1.1.1
-- 1.3.6.1.4.1.17409.1.1.1.1.1
-- 1.3.6.1.4.1.17409.1.1.1.1.1
-- 1.3.6.1.4.1.17409.1.1.1.1.1
-- 1.3.6.1.4.1.17409.1.1.1.1.1
-- 1.3.6.1.4.1.17409.1.1.1.1.1
-- 1.3.6.1.4.1.17409.1.1.1.1.1
-- 1.3.6.1.4.1.17409.1.1.1.1.1
		-- 1.3.6.1.4.1.17409.1.1.1.1.1
		analogParameterOID OBJECT-TYPE
			SYNTAX OBJECT IDENTIFIER
			MAX-ACCESS read-only
			STATUS current
			DESCRIPTION
				"索引。"
			::= { analogPropertyEntry 1 }

		
--         1.3.6.1.4.1.1.1.1.1.1.2
-- 1.3.6.1.4.1.17409.1.1.1.1.2
-- 1.3.6.1.4.1.17409.1.1.1.1.2
-- 1.3.6.1.4.1.17409.1.1.1.1.2
-- 1.3.6.1.4.1.17409.1.1.1.1.2
-- 1.3.6.1.4.1.17409.1.1.1.1.2
-- 1.3.6.1.4.1.17409.1.1.1.1.2
-- 1.3.6.1.4.1.17409.1.1.1.1.2
		-- 1.3.6.1.4.1.17409.1.1.1.1.2
		alarmEnable OBJECT-TYPE
			SYNTAX OCTET STRING (SIZE (1))
			MAX-ACCESS read-write
			STATUS current
			DESCRIPTION
				"告警使能控制字节，对应位为'1'表示允许告警,'0'表示禁止告警
				Bit 0 : 极低告警使能
				Bit 1 : 低告警使能
				Bit 2 : 高告警使能
				Bit 3 : 极高告警使能
				Bit 4～7 保留,应为0 
				此对象应保存在非易失性存储器中。"
			::= { analogPropertyEntry 2 }

		
--         1.3.6.1.4.1.1.1.1.1.1.3
-- 1.3.6.1.4.1.17409.1.1.1.1.3
-- 1.3.6.1.4.1.17409.1.1.1.1.3
-- 1.3.6.1.4.1.17409.1.1.1.1.3
-- 1.3.6.1.4.1.17409.1.1.1.1.3
-- 1.3.6.1.4.1.17409.1.1.1.1.3
-- 1.3.6.1.4.1.17409.1.1.1.1.3
-- 1.3.6.1.4.1.17409.1.1.1.1.3
		-- 1.3.6.1.4.1.17409.1.1.1.1.3
		analogAlarmState OBJECT-TYPE
			SYNTAX INTEGER
				{
				aasNominal(1),
				aasHIHI(2),
				aasHI(3),
				aasLO(4),
				aasLOLO(5)
				}
			MAX-ACCESS read-only
			STATUS current
			DESCRIPTION
				"参数的当前告警状态。"
			::= { analogPropertyEntry 3 }

		
--         1.3.6.1.4.1.1.1.1.1.1.4
-- 1.3.6.1.4.1.17409.1.1.1.1.4
-- 1.3.6.1.4.1.17409.1.1.1.1.4
-- 1.3.6.1.4.1.17409.1.1.1.1.4
-- 1.3.6.1.4.1.17409.1.1.1.1.4
-- 1.3.6.1.4.1.17409.1.1.1.1.4
-- 1.3.6.1.4.1.17409.1.1.1.1.4
-- 1.3.6.1.4.1.17409.1.1.1.1.4
		-- 1.3.6.1.4.1.17409.1.1.1.1.4
		analogAlarmHIHI OBJECT-TYPE
			SYNTAX Integer32
			MAX-ACCESS read-write
			STATUS current
			DESCRIPTION
				"极高告警门限HIHI的值。此对象应保存在非易失性存储器中。"
			::= { analogPropertyEntry 4 }

		
--         1.3.6.1.4.1.1.1.1.1.1.5
-- 1.3.6.1.4.1.17409.1.1.1.1.5
-- 1.3.6.1.4.1.17409.1.1.1.1.5
-- 1.3.6.1.4.1.17409.1.1.1.1.5
-- 1.3.6.1.4.1.17409.1.1.1.1.5
-- 1.3.6.1.4.1.17409.1.1.1.1.5
-- 1.3.6.1.4.1.17409.1.1.1.1.5
-- 1.3.6.1.4.1.17409.1.1.1.1.5
		-- 1.3.6.1.4.1.17409.1.1.1.1.5
		analogAlarmHI OBJECT-TYPE
			SYNTAX Integer32
			MAX-ACCESS read-write
			STATUS current
			DESCRIPTION
				"高告警门限HI的值。此对象应保存在非易失性存储器中。"
			::= { analogPropertyEntry 5 }

		
--         1.3.6.1.4.1.1.1.1.1.1.6
-- 1.3.6.1.4.1.17409.1.1.1.1.6
-- 1.3.6.1.4.1.17409.1.1.1.1.6
-- 1.3.6.1.4.1.17409.1.1.1.1.6
-- 1.3.6.1.4.1.17409.1.1.1.1.6
-- 1.3.6.1.4.1.17409.1.1.1.1.6
-- 1.3.6.1.4.1.17409.1.1.1.1.6
-- 1.3.6.1.4.1.17409.1.1.1.1.6
		-- 1.3.6.1.4.1.17409.1.1.1.1.6
		analogAlarmLO OBJECT-TYPE
			SYNTAX Integer32
			MAX-ACCESS read-write
			STATUS current
			DESCRIPTION
				"低告警门限LO的值。此对象应保存在非易失性存储器中。"
			::= { analogPropertyEntry 6 }

		
--         1.3.6.1.4.1.1.1.1.1.1.7
-- 1.3.6.1.4.1.17409.1.1.1.1.7
-- 1.3.6.1.4.1.17409.1.1.1.1.7
-- 1.3.6.1.4.1.17409.1.1.1.1.7
-- 1.3.6.1.4.1.17409.1.1.1.1.7
-- 1.3.6.1.4.1.17409.1.1.1.1.7
-- 1.3.6.1.4.1.17409.1.1.1.1.7
-- 1.3.6.1.4.1.17409.1.1.1.1.7
		-- 1.3.6.1.4.1.17409.1.1.1.1.7
		analogAlarmLOLO OBJECT-TYPE
			SYNTAX Integer32
			MAX-ACCESS read-write
			STATUS current
			DESCRIPTION
				"极低告警门限LOLO的值。此对象应保存在非易失性存储器中。"
			::= { analogPropertyEntry 7 }

		
--         1.3.6.1.4.1.1.1.1.1.1.8
-- 1.3.6.1.4.1.17409.1.1.1.1.8
-- 1.3.6.1.4.1.17409.1.1.1.1.8
-- 1.3.6.1.4.1.17409.1.1.1.1.8
-- 1.3.6.1.4.1.17409.1.1.1.1.8
-- 1.3.6.1.4.1.17409.1.1.1.1.8
-- 1.3.6.1.4.1.17409.1.1.1.1.8
-- 1.3.6.1.4.1.17409.1.1.1.1.8
		-- 1.3.6.1.4.1.17409.1.1.1.1.8
		analogAlarmDeadband OBJECT-TYPE
			SYNTAX Integer32
			MAX-ACCESS read-write
			STATUS current
			DESCRIPTION
				"告警门限死区的值。告警产生后，参数值应恢复到告警门限内且与告警门限之差的绝对值大于死区值，该告警才能清除。
				此对象应保存在非易失性存储器中。"
			::= { analogPropertyEntry 8 }

		
--          *
-- * 离散属性表
-- * 离散属性表的记录数量是固定的，每个离散型参数的每一个需要进行告警处理的值在表
-- * 中均对应一条记录。每个离散型参数在离散属性表中至少对应有一条记录。
-- * 离散属性表有2个索引：一个是参数标识（OID），另一个是离散告警值（discreteAlarmValue）。
-- *
-- 1.3.6.1.4.1.1.1.1.2
-- 1.3.6.1.4.1.17409.1.1.2
-- 1.3.6.1.4.1.17409.1.1.2
-- 1.3.6.1.4.1.17409.1.1.2
-- 1.3.6.1.4.1.17409.1.1.2
-- 1.3.6.1.4.1.17409.1.1.2
-- 1.3.6.1.4.1.17409.1.1.2
-- 1.3.6.1.4.1.17409.1.1.2
		-- 1.3.6.1.4.1.17409.1.1.2
		discretePropertyTable OBJECT-TYPE
			SYNTAX SEQUENCE OF DiscretePropertyEntry
			MAX-ACCESS not-accessible
			STATUS current
			DESCRIPTION
				"离散属性表。"
			::= { propertyIdent 2 }

		
--         1.3.6.1.4.1.1.1.1.2.1
-- 1.3.6.1.4.1.17409.1.1.2.1
-- 1.3.6.1.4.1.17409.1.1.2.1
-- 1.3.6.1.4.1.17409.1.1.2.1
-- 1.3.6.1.4.1.17409.1.1.2.1
-- 1.3.6.1.4.1.17409.1.1.2.1
-- 1.3.6.1.4.1.17409.1.1.2.1
-- 1.3.6.1.4.1.17409.1.1.2.1
		-- 1.3.6.1.4.1.17409.1.1.2.1
		discretePropertyEntry OBJECT-TYPE
			SYNTAX DiscretePropertyEntry
			MAX-ACCESS not-accessible
			STATUS current
			DESCRIPTION
				"离散属性表目。OID的编码方式同模拟属性表。"
			INDEX { discreteParameterOID, discreteAlarmValue }
			::= { discretePropertyTable 1 }

		
		DiscretePropertyEntry ::=
			SEQUENCE { 
				discreteParameterOID
					OBJECT IDENTIFIER,
				discreteAlarmValue
					Integer32,
				discreteAlarmEnable
					INTEGER,
				discreteAlarmState
					INTEGER
			 }

--         1.3.6.1.4.1.1.1.1.2.1.1
-- 1.3.6.1.4.1.17409.1.1.2.1.1
-- 1.3.6.1.4.1.17409.1.1.2.1.1
-- 1.3.6.1.4.1.17409.1.1.2.1.1
-- 1.3.6.1.4.1.17409.1.1.2.1.1
-- 1.3.6.1.4.1.17409.1.1.2.1.1
-- 1.3.6.1.4.1.17409.1.1.2.1.1
-- 1.3.6.1.4.1.17409.1.1.2.1.1
		-- 1.3.6.1.4.1.17409.1.1.2.1.1
		discreteParameterOID OBJECT-TYPE
			SYNTAX OBJECT IDENTIFIER
			MAX-ACCESS read-only
			STATUS current
			DESCRIPTION
				"离散属性表的索引1：参数OID。"
			::= { discretePropertyEntry 1 }

		
--         1.3.6.1.4.1.1.1.1.2.1.2
-- 1.3.6.1.4.1.17409.1.1.2.1.2
-- 1.3.6.1.4.1.17409.1.1.2.1.2
-- 1.3.6.1.4.1.17409.1.1.2.1.2
-- 1.3.6.1.4.1.17409.1.1.2.1.2
-- 1.3.6.1.4.1.17409.1.1.2.1.2
-- 1.3.6.1.4.1.17409.1.1.2.1.2
-- 1.3.6.1.4.1.17409.1.1.2.1.2
		-- 1.3.6.1.4.1.17409.1.1.2.1.2
		discreteAlarmValue OBJECT-TYPE
			SYNTAX Integer32
			MAX-ACCESS read-only
			STATUS current
			DESCRIPTION
				"离散属性表的索引2：参数值。
				当设备的参数值等于此值，将进行告警处理。"
			::= { discretePropertyEntry 2 }

		
--         1.3.6.1.4.1.1.1.1.2.1.3
-- 1.3.6.1.4.1.17409.1.1.2.1.3
-- 1.3.6.1.4.1.17409.1.1.2.1.3
-- 1.3.6.1.4.1.17409.1.1.2.1.3
-- 1.3.6.1.4.1.17409.1.1.2.1.3
-- 1.3.6.1.4.1.17409.1.1.2.1.3
-- 1.3.6.1.4.1.17409.1.1.2.1.3
-- 1.3.6.1.4.1.17409.1.1.2.1.3
		-- 1.3.6.1.4.1.17409.1.1.2.1.3
		discreteAlarmEnable OBJECT-TYPE
			SYNTAX INTEGER
				{
				disable(1),
				enableMajor(2),
				enableMinor(3)
				}
			MAX-ACCESS read-write
			STATUS current
			DESCRIPTION
				"当告警使能打开(2或3)，允许进行此参数的告警处理。
				如果告警使能关闭(1)，则告警处理不会进行。
				此对象缺省值为disable(1)。
				此对象应保存在非易失性存储器中。"
			::= { discretePropertyEntry 3 }

		
--         1.3.6.1.4.1.1.1.1.2.1.4
-- 1.3.6.1.4.1.17409.1.1.2.1.4
-- 1.3.6.1.4.1.17409.1.1.2.1.4
-- 1.3.6.1.4.1.17409.1.1.2.1.4
-- 1.3.6.1.4.1.17409.1.1.2.1.4
-- 1.3.6.1.4.1.17409.1.1.2.1.4
-- 1.3.6.1.4.1.17409.1.1.2.1.4
-- 1.3.6.1.4.1.17409.1.1.2.1.4
		-- 1.3.6.1.4.1.17409.1.1.2.1.4
		discreteAlarmState OBJECT-TYPE
			SYNTAX INTEGER
				{
				dasNominal(1),
				dasDiscreteMajor(6),
				dasDiscreteMinor(7)
				}
			MAX-ACCESS read-only
			STATUS current
			DESCRIPTION
				"参数的当前告警状态。"
			::= { discretePropertyEntry 4 }

		
--          * 
-- * 当前告警表包含了NE当前处于"激活"状态的告警项(0项或多项)。
-- * 虽然模拟属性表和离散属性表中也包括了告警状态信息，但是管理者应遍历全表才能
-- * 完全确定NE的告警状态，在效率上比较低。而当前告警表的作用就是将这2张表中处于告警
-- * 状态的那些项进行了汇总，便于管理者进行检索。
-- * 建议管理者程序使用GetNext命令(从表头OID开始)遍历这张表来获取NE所有的告警信息。
-- * HFC网络正常工作时，当前告警表的内容为空。
-- * 
-- 1.3.6.1.4.1.1.1.1.3
-- 1.3.6.1.4.1.17409.1.1.3
-- 1.3.6.1.4.1.17409.1.1.3
-- 1.3.6.1.4.1.17409.1.1.3
-- 1.3.6.1.4.1.17409.1.1.3
-- 1.3.6.1.4.1.17409.1.1.3
-- 1.3.6.1.4.1.17409.1.1.3
-- 1.3.6.1.4.1.17409.1.1.3
		-- 1.3.6.1.4.1.17409.1.1.3
		currentAlarmTable OBJECT-TYPE
			SYNTAX SEQUENCE OF CurrentAlarmEntry
			MAX-ACCESS not-accessible
			STATUS current
			DESCRIPTION
				"当前告警表。"
			::= { propertyIdent 3 }

		
--         1.3.6.1.4.1.1.1.1.3.1
-- 1.3.6.1.4.1.17409.1.1.3.1
-- 1.3.6.1.4.1.17409.1.1.3.1
-- 1.3.6.1.4.1.17409.1.1.3.1
-- 1.3.6.1.4.1.17409.1.1.3.1
-- 1.3.6.1.4.1.17409.1.1.3.1
-- 1.3.6.1.4.1.17409.1.1.3.1
-- 1.3.6.1.4.1.17409.1.1.3.1
		-- 1.3.6.1.4.1.17409.1.1.3.1
		currentAlarmEntry OBJECT-TYPE
			SYNTAX CurrentAlarmEntry
			MAX-ACCESS not-accessible
			STATUS current
			DESCRIPTION
				"当前告警表目。
				OID的编码方式同模拟属性表。"
			INDEX { currentAlarmOID }
			::= { currentAlarmTable 1 }

		
		CurrentAlarmEntry ::=
			SEQUENCE { 
				currentAlarmOID
					OBJECT IDENTIFIER,
				currentAlarmState
					INTEGER,
				currentAlarmValue
					Integer32
			 }

--         1.3.6.1.4.1.1.1.1.3.1.1
-- 1.3.6.1.4.1.17409.1.1.3.1.1
-- 1.3.6.1.4.1.17409.1.1.3.1.1
-- 1.3.6.1.4.1.17409.1.1.3.1.1
-- 1.3.6.1.4.1.17409.1.1.3.1.1
-- 1.3.6.1.4.1.17409.1.1.3.1.1
-- 1.3.6.1.4.1.17409.1.1.3.1.1
-- 1.3.6.1.4.1.17409.1.1.3.1.1
		-- 1.3.6.1.4.1.17409.1.1.3.1.1
		currentAlarmOID OBJECT-TYPE
			SYNTAX OBJECT IDENTIFIER
			MAX-ACCESS read-only
			STATUS current
			DESCRIPTION
				"NE当前处于告警状态的参数OID索引,与属性表中的告警参数OID对应。"
			::= { currentAlarmEntry 1 }

		
--         1.3.6.1.4.1.1.1.1.3.1.2
-- 1.3.6.1.4.1.17409.1.1.3.1.2
-- 1.3.6.1.4.1.17409.1.1.3.1.2
-- 1.3.6.1.4.1.17409.1.1.3.1.2
-- 1.3.6.1.4.1.17409.1.1.3.1.2
-- 1.3.6.1.4.1.17409.1.1.3.1.2
-- 1.3.6.1.4.1.17409.1.1.3.1.2
-- 1.3.6.1.4.1.17409.1.1.3.1.2
		-- 1.3.6.1.4.1.17409.1.1.3.1.2
		currentAlarmState OBJECT-TYPE
			SYNTAX INTEGER
				{
				caasHIHI(2),
				caasHI(3),
				caasLO(4),
				caasLOLO(5),
				caasDiscreteMajor(6),
				caasDiscreteMinor(7)
				}
			MAX-ACCESS read-only
			STATUS current
			DESCRIPTION
				"告警参数的当前告警状态。"
			::= { currentAlarmEntry 2 }

		
--         1.3.6.1.4.1.1.1.1.3.1.3
-- 1.3.6.1.4.1.17409.1.1.3.1.3
-- 1.3.6.1.4.1.17409.1.1.3.1.3
-- 1.3.6.1.4.1.17409.1.1.3.1.3
-- 1.3.6.1.4.1.17409.1.1.3.1.3
-- 1.3.6.1.4.1.17409.1.1.3.1.3
-- 1.3.6.1.4.1.17409.1.1.3.1.3
-- 1.3.6.1.4.1.17409.1.1.3.1.3
		-- 1.3.6.1.4.1.17409.1.1.3.1.3
		currentAlarmValue OBJECT-TYPE
			SYNTAX Integer32
			MAX-ACCESS read-only
			STATUS current
			DESCRIPTION
				"告警参数的值。"
			::= { currentAlarmEntry 3 }

		
--              DESCRIPTION
-- "属性(Property)MIB的分支节点标识。"
-- "见附录C。"
-- 1.3.6.1.4.1.1.1.2
-- 1.3.6.1.4.1.17409.1.2
-- 1.3.6.1.4.1.17409.1.2
-- 1.3.6.1.4.1.17409.1.2
-- 1.3.6.1.4.1.17409.1.2
-- 1.3.6.1.4.1.17409.1.2
-- 1.3.6.1.4.1.17409.1.2
-- 1.3.6.1.4.1.17409.1.2
		-- 1.3.6.1.4.1.17409.1.2
		alarmsIdent OBJECT IDENTIFIER ::= { nscrtvHFCemsTree 2 }

		
--         ************************************************************************************************
-- 告警MIB
-- ************************************************************************************************
-- 1.3.6.1.4.1.1.1.2.1
-- 1.3.6.1.4.1.17409.1.2.1
-- 1.3.6.1.4.1.17409.1.2.1
-- 1.3.6.1.4.1.17409.1.2.1
-- 1.3.6.1.4.1.17409.1.2.1
-- 1.3.6.1.4.1.17409.1.2.1
-- 1.3.6.1.4.1.17409.1.2.1
-- 1.3.6.1.4.1.17409.1.2.1
		-- 1.3.6.1.4.1.17409.1.2.1
		alarmLogNumberOfEntries OBJECT-TYPE
			SYNTAX Integer32
			MAX-ACCESS read-only
			STATUS current
			DESCRIPTION
				"告警记录表中的记录数量。"
			::= { alarmsIdent 1 }

		
--         1.3.6.1.4.1.1.1.2.2
-- 1.3.6.1.4.1.17409.1.2.2
-- 1.3.6.1.4.1.17409.1.2.2
-- 1.3.6.1.4.1.17409.1.2.2
-- 1.3.6.1.4.1.17409.1.2.2
-- 1.3.6.1.4.1.17409.1.2.2
-- 1.3.6.1.4.1.17409.1.2.2
-- 1.3.6.1.4.1.17409.1.2.2
		-- 1.3.6.1.4.1.17409.1.2.2
		alarmLogLastIndex OBJECT-TYPE
			SYNTAX Integer32
			MAX-ACCESS read-only
			STATUS current
			DESCRIPTION
				"最近一条告警记录的索引值。"
			::= { alarmsIdent 2 }

		
--         1.3.6.1.4.1.1.1.2.3
-- 1.3.6.1.4.1.17409.1.2.3
-- 1.3.6.1.4.1.17409.1.2.3
-- 1.3.6.1.4.1.17409.1.2.3
-- 1.3.6.1.4.1.17409.1.2.3
-- 1.3.6.1.4.1.17409.1.2.3
-- 1.3.6.1.4.1.17409.1.2.3
-- 1.3.6.1.4.1.17409.1.2.3
		-- 1.3.6.1.4.1.17409.1.2.3
		alarmLogTable OBJECT-TYPE
			SYNTAX SEQUENCE OF AlarmLogEntry
			MAX-ACCESS not-accessible
			STATUS current
			DESCRIPTION
				"告警记录表，至少支持16条记录。每次在表中登记一条新的记录时，管理代理（即应答器）应向管理者发送陷阱消息。"
			::= { alarmsIdent 3 }

		
--         1.3.6.1.4.1.1.1.2.3.1
-- 1.3.6.1.4.1.17409.1.2.3.1
-- 1.3.6.1.4.1.17409.1.2.3.1
-- 1.3.6.1.4.1.17409.1.2.3.1
-- 1.3.6.1.4.1.17409.1.2.3.1
-- 1.3.6.1.4.1.17409.1.2.3.1
-- 1.3.6.1.4.1.17409.1.2.3.1
-- 1.3.6.1.4.1.17409.1.2.3.1
		-- 1.3.6.1.4.1.17409.1.2.3.1
		alarmLogEntry OBJECT-TYPE
			SYNTAX AlarmLogEntry
			MAX-ACCESS not-accessible
			STATUS current
			DESCRIPTION
				"告警记录表目。"
			INDEX { alarmLogIndex }
			::= { alarmLogTable 1 }

		
		AlarmLogEntry ::=
			SEQUENCE { 
				alarmLogIndex
					INTEGER,
				alarmLogInformation
					OCTET STRING
			 }

--         1.3.6.1.4.1.1.1.2.3.1.1
-- 1.3.6.1.4.1.17409.1.2.3.1.1
-- 1.3.6.1.4.1.17409.1.2.3.1.1
-- 1.3.6.1.4.1.17409.1.2.3.1.1
-- 1.3.6.1.4.1.17409.1.2.3.1.1
-- 1.3.6.1.4.1.17409.1.2.3.1.1
-- 1.3.6.1.4.1.17409.1.2.3.1.1
-- 1.3.6.1.4.1.17409.1.2.3.1.1
		-- 1.3.6.1.4.1.17409.1.2.3.1.1
		alarmLogIndex OBJECT-TYPE
			SYNTAX INTEGER (1..32767)
			MAX-ACCESS read-only
			STATUS current
			DESCRIPTION
				"索引唯一标识告警记录表中的一条记录，索引值从1开始每次增加新纪录时加1，直到32767，下一条记录索引值重新从1开始。管理代理可根据存储容量选择删除最早的那些记录，具体实现细节在此不做规定。"
			::= { alarmLogEntry 1 }

		
--         1.3.6.1.4.1.1.1.2.3.1.2
-- 1.3.6.1.4.1.17409.1.2.3.1.2
-- 1.3.6.1.4.1.17409.1.2.3.1.2
-- 1.3.6.1.4.1.17409.1.2.3.1.2
-- 1.3.6.1.4.1.17409.1.2.3.1.2
-- 1.3.6.1.4.1.17409.1.2.3.1.2
-- 1.3.6.1.4.1.17409.1.2.3.1.2
-- 1.3.6.1.4.1.17409.1.2.3.1.2
		-- 1.3.6.1.4.1.17409.1.2.3.1.2
		alarmLogInformation OBJECT-TYPE
			SYNTAX OCTET STRING (SIZE (17..255))
			MAX-ACCESS read-only
			STATUS current
			DESCRIPTION
				"告警记录信息，多字节串，定义如下：
				字节 1～4: 告警发生时间(POSIX格式，最高有效字节在前)
				字节 5: 告警类型(枚举，定义见后)
				字节 6: 告警发生后commonNeStatus的值
				字节 7～m: 告警参数的对象标识符(基本编码规则（ASN.1）)
				字节 n～z: 告警参数值 (基本编码规则（ASN.1）)
				
				告警枚举类型：
				1 NOMINAL
				2 HIHI
				3 HI
				4 LO
				5 LOLO
				6 Discrete Major
				7 Discrete Minor "
			::= { alarmLogEntry 2 }

		
--         1.3.6.1.4.1.1.1.2.4
-- 1.3.6.1.4.1.17409.1.2.4
-- 1.3.6.1.4.1.17409.1.2.4
-- 1.3.6.1.4.1.17409.1.2.4
-- 1.3.6.1.4.1.17409.1.2.4
-- 1.3.6.1.4.1.17409.1.2.4
-- 1.3.6.1.4.1.17409.1.2.4
-- 1.3.6.1.4.1.17409.1.2.4
		-- 1.3.6.1.4.1.17409.1.2.4
		alarmText OBJECT-TYPE
			SYNTAX DisplayString
			MAX-ACCESS not-accessible
			STATUS optional
			DESCRIPTION
				"此对象对于需要在陷阱消息中包含一个文本信息字段的应答器是应实现的。
				该字段中包含的文本内容取决于告警参数对象的定义，因此是不确定的，所以
				规定此对象不能访问。"
			::= { alarmsIdent 4 }

		
--              DESCRIPTION
-- "告警(Alarms)MIB的分支节点标识。"
-- "见附录D。"
-- 1.3.6.1.4.1.1.1.3
-- 1.3.6.1.4.1.17409.1.3
-- 1.3.6.1.4.1.17409.1.3
-- 1.3.6.1.4.1.17409.1.3
-- 1.3.6.1.4.1.17409.1.3
-- 1.3.6.1.4.1.17409.1.3
-- 1.3.6.1.4.1.17409.1.3
-- 1.3.6.1.4.1.17409.1.3
		-- 1.3.6.1.4.1.17409.1.3
		commonIdent OBJECT IDENTIFIER ::= { nscrtvHFCemsTree 3 }

		
--         ***********************************************************************************************
-- 公用MIB
-- **********************************************************************************************
-- *
-- *  Common MIB中使用的分组定义
-- *
-- 1.3.6.1.4.1.1.1.3.1
-- 1.3.6.1.4.1.17409.1.3.1
-- 1.3.6.1.4.1.17409.1.3.1
-- 1.3.6.1.4.1.17409.1.3.1
-- 1.3.6.1.4.1.17409.1.3.1
-- 1.3.6.1.4.1.17409.1.3.1
-- 1.3.6.1.4.1.17409.1.3.1
-- 1.3.6.1.4.1.17409.1.3.1
		-- 1.3.6.1.4.1.17409.1.3.1
		commonAdminGroup OBJECT IDENTIFIER ::= { commonIdent 1 }

		
--          *************
-- *   NE管理组
-- *************
-- 1.3.6.1.4.1.1.1.3.1.1
-- 1.3.6.1.4.1.17409.1.3.1.1
-- 1.3.6.1.4.1.17409.1.3.1.1
-- 1.3.6.1.4.1.17409.1.3.1.1
-- 1.3.6.1.4.1.17409.1.3.1.1
-- 1.3.6.1.4.1.17409.1.3.1.1
-- 1.3.6.1.4.1.17409.1.3.1.1
-- 1.3.6.1.4.1.17409.1.3.1.1
		-- 1.3.6.1.4.1.17409.1.3.1.1
		commonNELogicalID OBJECT-TYPE
			SYNTAX OCTET STRING (SIZE (0..40))
			MAX-ACCESS read-write
			STATUS current
			DESCRIPTION
				"指定NE的逻辑标识符（LogicID），此值一般与NE的其他属性无关。
				此对象值应存放在非易失性存储器中。"
			::= { commonAdminGroup 1 }

		
--         1.3.6.1.4.1.1.1.3.1.2
-- 1.3.6.1.4.1.17409.1.3.1.2
-- 1.3.6.1.4.1.17409.1.3.1.2
-- 1.3.6.1.4.1.17409.1.3.1.2
-- 1.3.6.1.4.1.17409.1.3.1.2
-- 1.3.6.1.4.1.17409.1.3.1.2
-- 1.3.6.1.4.1.17409.1.3.1.2
-- 1.3.6.1.4.1.17409.1.3.1.2
		-- 1.3.6.1.4.1.17409.1.3.1.2
		commonNEVendor OBJECT-TYPE
			SYNTAX DisplayString (SIZE (0..255))
			MAX-ACCESS read-only
			STATUS current
			DESCRIPTION
				"NE设备生产厂家。"
			::= { commonAdminGroup 2 }

		
--         1.3.6.1.4.1.1.1.3.1.3
-- 1.3.6.1.4.1.17409.1.3.1.3
-- 1.3.6.1.4.1.17409.1.3.1.3
-- 1.3.6.1.4.1.17409.1.3.1.3
-- 1.3.6.1.4.1.17409.1.3.1.3
-- 1.3.6.1.4.1.17409.1.3.1.3
-- 1.3.6.1.4.1.17409.1.3.1.3
-- 1.3.6.1.4.1.17409.1.3.1.3
		-- 1.3.6.1.4.1.17409.1.3.1.3
		commonNEModelNumber OBJECT-TYPE
			SYNTAX DisplayString (SIZE (0..255))
			MAX-ACCESS read-only
			STATUS current
			DESCRIPTION
				"NE设备的型号。"
			::= { commonAdminGroup 3 }

		
--         1.3.6.1.4.1.1.1.3.1.4
-- 1.3.6.1.4.1.17409.1.3.1.4
-- 1.3.6.1.4.1.17409.1.3.1.4
-- 1.3.6.1.4.1.17409.1.3.1.4
-- 1.3.6.1.4.1.17409.1.3.1.4
-- 1.3.6.1.4.1.17409.1.3.1.4
-- 1.3.6.1.4.1.17409.1.3.1.4
-- 1.3.6.1.4.1.17409.1.3.1.4
		-- 1.3.6.1.4.1.17409.1.3.1.4
		commonNESerialNumber OBJECT-TYPE
			SYNTAX DisplayString (SIZE (0..255))
			MAX-ACCESS read-only
			STATUS current
			DESCRIPTION
				"NE设备的序列号。"
			::= { commonAdminGroup 4 }

		
--         1.3.6.1.4.1.1.1.3.1.5
-- 1.3.6.1.4.1.17409.1.3.1.5
-- 1.3.6.1.4.1.17409.1.3.1.5
-- 1.3.6.1.4.1.17409.1.3.1.5
-- 1.3.6.1.4.1.17409.1.3.1.5
-- 1.3.6.1.4.1.17409.1.3.1.5
-- 1.3.6.1.4.1.17409.1.3.1.5
-- 1.3.6.1.4.1.17409.1.3.1.5
		-- 1.3.6.1.4.1.17409.1.3.1.5
		commonNEVendorInfo OBJECT-TYPE
			SYNTAX DisplayString (SIZE (0..255))
			MAX-ACCESS read-only
			STATUS optional
			DESCRIPTION
				"NE设备供应商的其它特殊指定信息。"
			::= { commonAdminGroup 5 }

		
--         1.3.6.1.4.1.1.1.3.1.6
-- 1.3.6.1.4.1.17409.1.3.1.6
-- 1.3.6.1.4.1.17409.1.3.1.6
-- 1.3.6.1.4.1.17409.1.3.1.6
-- 1.3.6.1.4.1.17409.1.3.1.6
-- 1.3.6.1.4.1.17409.1.3.1.6
-- 1.3.6.1.4.1.17409.1.3.1.6
-- 1.3.6.1.4.1.17409.1.3.1.6
		-- 1.3.6.1.4.1.17409.1.3.1.6
		commonNEStatus OBJECT-TYPE
			SYNTAX OCTET STRING (SIZE (1))
			MAX-ACCESS read-only
			STATUS current
			DESCRIPTION
				"与7.5.4 STATRESP PDU中的Status参数对应
				Bit 0: CHNLRQST
				Bit 1: CNTNRM
				Bit 2: CNTCUR
				Bit 3: MAJOR ALARMS
				Bit 4: MINOR ALARMS
				Bit 5: RSVD1
				Bit 6: RSVD2
				Bit 7: RSVD3"
			::= { commonAdminGroup 6 }

		
--         1.3.6.1.4.1.1.1.3.1.7
-- 1.3.6.1.4.1.17409.1.3.1.7
-- 1.3.6.1.4.1.17409.1.3.1.7
-- 1.3.6.1.4.1.17409.1.3.1.7
-- 1.3.6.1.4.1.17409.1.3.1.7
-- 1.3.6.1.4.1.17409.1.3.1.7
-- 1.3.6.1.4.1.17409.1.3.1.7
-- 1.3.6.1.4.1.17409.1.3.1.7
		-- 1.3.6.1.4.1.17409.1.3.1.7
		commonReset OBJECT-TYPE
			SYNTAX INTEGER { reset(1) }
			MAX-ACCESS read-write
			STATUS current
			DESCRIPTION
				"写入'1'将复位NE设备，写入其它值将不起作用。读此对象时返回值'1'，对设备无影响。"
			::= { commonAdminGroup 7 }

		
--         1.3.6.1.4.1.1.1.3.1.8
-- 1.3.6.1.4.1.17409.1.3.1.8
-- 1.3.6.1.4.1.17409.1.3.1.8
-- 1.3.6.1.4.1.17409.1.3.1.8
-- 1.3.6.1.4.1.17409.1.3.1.8
-- 1.3.6.1.4.1.17409.1.3.1.8
-- 1.3.6.1.4.1.17409.1.3.1.8
-- 1.3.6.1.4.1.17409.1.3.1.8
		-- 1.3.6.1.4.1.17409.1.3.1.8
		commonAlarmDetectionControl OBJECT-TYPE
			SYNTAX INTEGER
				{
				detectionDisabled(1),
				detectionEnabled(2),
				detectionEnabledAndRegenerate(3)
				}
			MAX-ACCESS read-write
			STATUS current
			DESCRIPTION
				"此对象用于控制NE的告警检测。
				当模拟属性表或离散属性表中的一个MIB对象达到设定的门限，就认为告警已发生，并且作为最新的告警记录在告警记录表（alarmLogTable）中添加一项，告警陷阱将同时产生。如有一个MIB对象的值不在正常状态，则在当前告警表（currentAlarmTable）中也会添加一项记录。
				          
				detectionDisabled(1)将停止与模拟属性表/离散属性表相关的告警检测过程，NE将不再产生告警。detectionEnabled(2)允许告警检测进行，检测从detectionEnabled被设置之前应答器所处的状态开始继续进行。
				
				detectionEnabledAndRegenerate(3)清除所有告警信息并且允许告警检测进行。模拟属性表和离散属性表的所有告警属性将恢复到告警检测运行之前的正常值上。任何仍处于告警状态的属性将不会产生'恢复正常'告警，设置此值将清除告警记录表alarmLogTable和当前告警表currentAlarmTable的内容。
				        
				detectionEnabledAndRegenerate的作用是临时的，当将commonAlarmDetectionControl设置为detectionEnabledAndRegnerate后，其SNMP应答包含此值，以后如果再读此对象值时，响应为detectionEnabled。
				        
				detectionDisabled值不影响hfcColdStart 或hfcWarmStart 陷阱的产生。
				将来新增的陷阱除非在其描述中有专门规定，否则一律不受此对象的影响。
				
				此对象应保存在非易失性存储器中，缺省值为detectionEnabled。"
			::= { commonAdminGroup 8 }

		
--         1.3.6.1.4.1.1.1.3.1.9
-- 1.3.6.1.4.1.17409.1.3.1.9
-- 1.3.6.1.4.1.17409.1.3.1.9
-- 1.3.6.1.4.1.17409.1.3.1.9
-- 1.3.6.1.4.1.17409.1.3.1.9
-- 1.3.6.1.4.1.17409.1.3.1.9
-- 1.3.6.1.4.1.17409.1.3.1.9
-- 1.3.6.1.4.1.17409.1.3.1.9
		-- 1.3.6.1.4.1.17409.1.3.1.9
		commonNetworkAddress OBJECT-TYPE
			SYNTAX IpAddress
			MAX-ACCESS read-only
			STATUS current
			DESCRIPTION
				"NE的网络IP地址，NE产生Trap时应包含此地址。此值应保存在非易失性存储器中。此值可以在注册时通过MAC命令或通过厂商的本地接口来设置。"
			::= { commonAdminGroup 9 }

		
--         1.3.6.1.4.1.1.1.3.1.10
-- 1.3.6.1.4.1.17409.1.3.1.10
-- 1.3.6.1.4.1.17409.1.3.1.10
-- 1.3.6.1.4.1.17409.1.3.1.10
-- 1.3.6.1.4.1.17409.1.3.1.10
-- 1.3.6.1.4.1.17409.1.3.1.10
-- 1.3.6.1.4.1.17409.1.3.1.10
-- 1.3.6.1.4.1.17409.1.3.1.10
		-- 1.3.6.1.4.1.17409.1.3.1.10
		commonCheckCode OBJECT-TYPE
			SYNTAX Integer32
			MAX-ACCESS read-write
			STATUS current
			DESCRIPTION
				"此对象用于应答器配置的检测码的报告。检测码的计算包括应答器（包括被管理设备）的物理配置参数和存放在非易失性存储器中的所有对象参数。计算检测码的算法由厂商规定。
				该对象的值应保存在非易失性存储器中，应答器重启动时，将重新计算检测码并与重启动前的值进行比较，以决定是否应产生一个hfcColdStart 或 hfcWarmStart陷阱。          
				当对此对象进行写操作（SetRequest）时，检测码将被重新计算，并填入对SetRequest作出的GetResponse应答中。此时，将不产生hfcColdStart 或 hfcWarmStart 陷阱。"
			::= { commonAdminGroup 10 }

		
--         1.3.6.1.4.1.1.1.3.1.11
-- 1.3.6.1.4.1.17409.1.3.1.11
-- 1.3.6.1.4.1.17409.1.3.1.11
-- 1.3.6.1.4.1.17409.1.3.1.11
-- 1.3.6.1.4.1.17409.1.3.1.11
-- 1.3.6.1.4.1.17409.1.3.1.11
-- 1.3.6.1.4.1.17409.1.3.1.11
-- 1.3.6.1.4.1.17409.1.3.1.11
		-- 1.3.6.1.4.1.17409.1.3.1.11
		commonTrapCommunityString OBJECT-TYPE
			SYNTAX OCTET STRING (SIZE (0..64))
			MAX-ACCESS read-write
			STATUS current
			DESCRIPTION
				"定义Trap中的共同体字符串。缺省值是'public'。
				此对象的值应保存在非易失性存储器中。"
			::= { commonAdminGroup 11 }

		
--         1.3.6.1.4.1.1.1.3.1.12
-- 1.3.6.1.4.1.17409.1.3.1.12
-- 1.3.6.1.4.1.17409.1.3.1.12
-- 1.3.6.1.4.1.17409.1.3.1.12
-- 1.3.6.1.4.1.17409.1.3.1.12
-- 1.3.6.1.4.1.17409.1.3.1.12
-- 1.3.6.1.4.1.17409.1.3.1.12
-- 1.3.6.1.4.1.17409.1.3.1.12
		-- 1.3.6.1.4.1.17409.1.3.1.12
		commonTamperStatus OBJECT-TYPE
			SYNTAX INTEGER
				{
				intact(1),
				compromised(2)
				}
			MAX-ACCESS read-only
			STATUS optional
			DESCRIPTION
				"报告NE设备的安全开关(如盖子是否打开)状态，此对象要求在离散属性表中对应一个条目。intact表示正常，compromised表示告警"
			::= { commonAdminGroup 12 }

		
--         1.3.6.1.4.1.1.1.3.1.13
-- 1.3.6.1.4.1.17409.1.3.1.13
-- 1.3.6.1.4.1.17409.1.3.1.13
-- 1.3.6.1.4.1.17409.1.3.1.13
-- 1.3.6.1.4.1.17409.1.3.1.13
-- 1.3.6.1.4.1.17409.1.3.1.13
-- 1.3.6.1.4.1.17409.1.3.1.13
-- 1.3.6.1.4.1.17409.1.3.1.13
		-- 1.3.6.1.4.1.17409.1.3.1.13
		commonInternalTemperature OBJECT-TYPE
			SYNTAX INTEGER (-128..127)
			MAX-ACCESS read-only
			STATUS optional
			DESCRIPTION
				"NE设备的室（机）内温度，单位为摄氏度。此对象要求在属性表中对应一个条目。"
			::= { commonAdminGroup 13 }

		
--         1.3.6.1.4.1.1.1.3.1.14
-- 1.3.6.1.4.1.17409.1.3.1.14
-- 1.3.6.1.4.1.17409.1.3.1.14
-- 1.3.6.1.4.1.17409.1.3.1.14
-- 1.3.6.1.4.1.17409.1.3.1.14
-- 1.3.6.1.4.1.17409.1.3.1.14
-- 1.3.6.1.4.1.17409.1.3.1.14
-- 1.3.6.1.4.1.17409.1.3.1.14
		-- 1.3.6.1.4.1.17409.1.3.1.14
		commonTime OBJECT-TYPE
			SYNTAX Integer32
			MAX-ACCESS read-write
			STATUS optional
			DESCRIPTION
				"NE的当前时间的POSIX表示（自1970年1月1日0时以来的秒数）。"
			::= { commonAdminGroup 14 }

		
--         1.3.6.1.4.1.1.1.3.1.15
-- 1.3.6.1.4.1.17409.1.3.1.15
-- 1.3.6.1.4.1.17409.1.3.1.15
-- 1.3.6.1.4.1.17409.1.3.1.15
-- 1.3.6.1.4.1.17409.1.3.1.15
-- 1.3.6.1.4.1.17409.1.3.1.15
-- 1.3.6.1.4.1.17409.1.3.1.15
-- 1.3.6.1.4.1.17409.1.3.1.15
		-- 1.3.6.1.4.1.17409.1.3.1.15
		commonVarBindings OBJECT-TYPE
			SYNTAX Integer32
			MAX-ACCESS read-only
			STATUS current
			DESCRIPTION
				"此对象表示能被NE接收的SNMP消息变量绑定表项的最大数目。其值为0表示对绑定最大数目没有限制。"
			::= { commonAdminGroup 15 }

		
--         1.3.6.1.4.1.1.1.3.1.16
-- 1.3.6.1.4.1.17409.1.3.1.16
-- 1.3.6.1.4.1.17409.1.3.1.16
-- 1.3.6.1.4.1.17409.1.3.1.16
-- 1.3.6.1.4.1.17409.1.3.1.16
-- 1.3.6.1.4.1.17409.1.3.1.16
-- 1.3.6.1.4.1.17409.1.3.1.16
-- 1.3.6.1.4.1.17409.1.3.1.16
		-- 1.3.6.1.4.1.17409.1.3.1.16
		commonResetCause OBJECT-TYPE
			SYNTAX INTEGER
				{
				other(1),
				powerup(2),
				command(3),
				watchdog(4),
				craft(5)
				}
			MAX-ACCESS read-only
			STATUS current
			DESCRIPTION
				"表示NE最近一次复位的原因。"
			::= { commonAdminGroup 16 }

		
--         1.3.6.1.4.1.1.1.3.1.17
-- 1.3.6.1.4.1.17409.1.3.1.17
-- 1.3.6.1.4.1.17409.1.3.1.17
-- 1.3.6.1.4.1.17409.1.3.1.17
-- 1.3.6.1.4.1.17409.1.3.1.17
-- 1.3.6.1.4.1.17409.1.3.1.17
-- 1.3.6.1.4.1.17409.1.3.1.17
-- 1.3.6.1.4.1.17409.1.3.1.17
		-- 1.3.6.1.4.1.17409.1.3.1.17
		commonCraftStatus OBJECT-TYPE
			SYNTAX INTEGER
				{
				disconnected(1),
				connected(2)
				}
			MAX-ACCESS read-only
			STATUS current
			DESCRIPTION
				"此对象表示NE本地接口（如RS232或RS485接口）的状态。NE并不一定要支持本地接口。
				NE本地接口的状态不影响其MAC接口的功能；如果不支持本地接口，其值为disconnected。"
			::= { commonAdminGroup 17 }

		
--         1.3.6.1.4.1.1.1.3.1.18
-- 1.3.6.1.4.1.17409.1.3.1.18
-- 1.3.6.1.4.1.17409.1.3.1.18
-- 1.3.6.1.4.1.17409.1.3.1.18
-- 1.3.6.1.4.1.17409.1.3.1.18
-- 1.3.6.1.4.1.17409.1.3.1.18
-- 1.3.6.1.4.1.17409.1.3.1.18
-- 1.3.6.1.4.1.17409.1.3.1.18
		-- 1.3.6.1.4.1.17409.1.3.1.18
		commonDeviceOID OBJECT-TYPE
			SYNTAX OBJECT IDENTIFIER
			MAX-ACCESS read-only
			STATUS optional
			DESCRIPTION
				"此对象为一个OID指针，用于指向被管设备MIB(如光节点、双向放大器等)。 "
			::= { commonAdminGroup 18 }

		
--         1.3.6.1.4.1.1.1.3.1.19
-- 1.3.6.1.4.1.17409.1.3.1.19
-- 1.3.6.1.4.1.17409.1.3.1.19
-- 1.3.6.1.4.1.17409.1.3.1.19
-- 1.3.6.1.4.1.17409.1.3.1.19
-- 1.3.6.1.4.1.17409.1.3.1.19
-- 1.3.6.1.4.1.17409.1.3.1.19
-- 1.3.6.1.4.1.17409.1.3.1.19
		-- 1.3.6.1.4.1.17409.1.3.1.19
		commonDeviceId OBJECT-TYPE
			SYNTAX OCTET STRING (SIZE (32))
			MAX-ACCESS read-only
			STATUS optional
			DESCRIPTION
				"此对象的内容由被管设备厂商指定，它包含厂商和产品的特殊的ASCII码文本信息。"
			::= { commonAdminGroup 19 }

		
--         1.3.6.1.4.1.1.1.3.2
-- 1.3.6.1.4.1.17409.1.3.2
-- 1.3.6.1.4.1.17409.1.3.2
-- 1.3.6.1.4.1.17409.1.3.2
-- 1.3.6.1.4.1.17409.1.3.2
-- 1.3.6.1.4.1.17409.1.3.2
-- 1.3.6.1.4.1.17409.1.3.2
-- 1.3.6.1.4.1.17409.1.3.2
		-- 1.3.6.1.4.1.17409.1.3.2
		commonAdminUseRf OBJECT IDENTIFIER ::= { commonIdent 2 }

		
--         1.3.6.1.4.1.1.1.3.2.1
-- 1.3.6.1.4.1.17409.1.3.2.1
-- 1.3.6.1.4.1.17409.1.3.2.1
-- 1.3.6.1.4.1.17409.1.3.2.1
-- 1.3.6.1.4.1.17409.1.3.2.1
-- 1.3.6.1.4.1.17409.1.3.2.1
-- 1.3.6.1.4.1.17409.1.3.2.1
-- 1.3.6.1.4.1.17409.1.3.2.1
		-- 1.3.6.1.4.1.17409.1.3.2.1
		commonMACGroup OBJECT IDENTIFIER ::= { commonAdminUseRf 1 }

		
--         1.3.6.1.4.1.1.1.3.2.1.1
-- 1.3.6.1.4.1.17409.1.3.2.1.1
-- 1.3.6.1.4.1.17409.1.3.2.1.1
-- 1.3.6.1.4.1.17409.1.3.2.1.1
-- 1.3.6.1.4.1.17409.1.3.2.1.1
-- 1.3.6.1.4.1.17409.1.3.2.1.1
-- 1.3.6.1.4.1.17409.1.3.2.1.1
-- 1.3.6.1.4.1.17409.1.3.2.1.1
		-- 1.3.6.1.4.1.17409.1.3.2.1.1
		commonMacAddress OBJECT IDENTIFIER ::= { commonMACGroup 1 }

		
--          ******************
-- *  MAC层协议管理组
-- *******************
-- ****************
-- *   NE地址管理
-- ****************
-- 1.3.6.1.4.1.1.1.3.2.1.1.1
-- 1.3.6.1.4.1.17409.1.3.2.1.1.1
-- 1.3.6.1.4.1.17409.1.3.2.1.1.1
-- 1.3.6.1.4.1.17409.1.3.2.1.1.1
-- 1.3.6.1.4.1.17409.1.3.2.1.1.1
-- 1.3.6.1.4.1.17409.1.3.2.1.1.1
-- 1.3.6.1.4.1.17409.1.3.2.1.1.1
-- 1.3.6.1.4.1.17409.1.3.2.1.1.1
		-- 1.3.6.1.4.1.17409.1.3.2.1.1.1
		commonPhysAddress OBJECT-TYPE
			SYNTAX OCTET STRING
			MAX-ACCESS read-only
			STATUS current
			DESCRIPTION
				"NE的MAC（物理）地址。"
			::= { commonMacAddress 1 }

		
--         1.3.6.1.4.1.1.1.3.2.1.1.2
-- 1.3.6.1.4.1.17409.1.3.2.1.1.2
-- 1.3.6.1.4.1.17409.1.3.2.1.1.2
-- 1.3.6.1.4.1.17409.1.3.2.1.1.2
-- 1.3.6.1.4.1.17409.1.3.2.1.1.2
-- 1.3.6.1.4.1.17409.1.3.2.1.1.2
-- 1.3.6.1.4.1.17409.1.3.2.1.1.2
-- 1.3.6.1.4.1.17409.1.3.2.1.1.2
		-- 1.3.6.1.4.1.17409.1.3.2.1.1.2
		commonMaxMulticastAddresses OBJECT-TYPE
			SYNTAX INTEGER (4..255)
			MAX-ACCESS read-only
			STATUS current
			DESCRIPTION
				"NE设备支持的最大组播地址数目。"
			::= { commonMacAddress 2 }

		
--         1.3.6.1.4.1.1.1.3.2.1.1.3
-- 1.3.6.1.4.1.17409.1.3.2.1.1.3
-- 1.3.6.1.4.1.17409.1.3.2.1.1.3
-- 1.3.6.1.4.1.17409.1.3.2.1.1.3
-- 1.3.6.1.4.1.17409.1.3.2.1.1.3
-- 1.3.6.1.4.1.17409.1.3.2.1.1.3
-- 1.3.6.1.4.1.17409.1.3.2.1.1.3
-- 1.3.6.1.4.1.17409.1.3.2.1.1.3
		-- 1.3.6.1.4.1.17409.1.3.2.1.1.3
		commonMulticastAddressTable OBJECT-TYPE
			SYNTAX SEQUENCE OF CommonMulticastAddressEntry
			MAX-ACCESS not-accessible
			STATUS current
			DESCRIPTION
				"组播地址表，此对象的值应保存在非易失性存储器中。"
			::= { commonMacAddress 3 }

		
--         1.3.6.1.4.1.1.1.3.2.1.1.3.1
-- 1.3.6.1.4.1.17409.1.3.2.1.1.3.1
-- 1.3.6.1.4.1.17409.1.3.2.1.1.3.1
-- 1.3.6.1.4.1.17409.1.3.2.1.1.3.1
-- 1.3.6.1.4.1.17409.1.3.2.1.1.3.1
-- 1.3.6.1.4.1.17409.1.3.2.1.1.3.1
-- 1.3.6.1.4.1.17409.1.3.2.1.1.3.1
-- 1.3.6.1.4.1.17409.1.3.2.1.1.3.1
		-- 1.3.6.1.4.1.17409.1.3.2.1.1.3.1
		commonMulticastAddressEntry OBJECT-TYPE
			SYNTAX CommonMulticastAddressEntry
			MAX-ACCESS not-accessible
			STATUS current
			DESCRIPTION
				"组播地址表目。"
			INDEX { commonMulticastAddressIndex }
			::= { commonMulticastAddressTable 1 }

		
		CommonMulticastAddressEntry ::=
			SEQUENCE { 
				commonMulticastAddressIndex
					INTEGER,
				commonMulticastAddressNumber
					OCTET STRING
			 }

--         1.3.6.1.4.1.1.1.3.2.1.1.3.1.1
-- 1.3.6.1.4.1.17409.1.3.2.1.1.3.1.1
-- 1.3.6.1.4.1.17409.1.3.2.1.1.3.1.1
-- 1.3.6.1.4.1.17409.1.3.2.1.1.3.1.1
-- 1.3.6.1.4.1.17409.1.3.2.1.1.3.1.1
-- 1.3.6.1.4.1.17409.1.3.2.1.1.3.1.1
-- 1.3.6.1.4.1.17409.1.3.2.1.1.3.1.1
-- 1.3.6.1.4.1.17409.1.3.2.1.1.3.1.1
		-- 1.3.6.1.4.1.17409.1.3.2.1.1.3.1.1
		commonMulticastAddressIndex OBJECT-TYPE
			SYNTAX INTEGER (1..255)
			MAX-ACCESS read-only
			STATUS current
			DESCRIPTION
				"组播地址索引。"
			::= { commonMulticastAddressEntry 1 }

		
--         1.3.6.1.4.1.1.1.3.2.1.1.3.1.2
-- 1.3.6.1.4.1.17409.1.3.2.1.1.3.1.2
-- 1.3.6.1.4.1.17409.1.3.2.1.1.3.1.2
-- 1.3.6.1.4.1.17409.1.3.2.1.1.3.1.2
-- 1.3.6.1.4.1.17409.1.3.2.1.1.3.1.2
-- 1.3.6.1.4.1.17409.1.3.2.1.1.3.1.2
-- 1.3.6.1.4.1.17409.1.3.2.1.1.3.1.2
-- 1.3.6.1.4.1.17409.1.3.2.1.1.3.1.2
		-- 1.3.6.1.4.1.17409.1.3.2.1.1.3.1.2
		commonMulticastAddressNumber OBJECT-TYPE
			SYNTAX OCTET STRING (SIZE (6))
			MAX-ACCESS read-write
			STATUS current
			DESCRIPTION
				"组播地址，I/G位为1有效。"
			::= { commonMulticastAddressEntry 2 }

		
--         1.3.6.1.4.1.1.1.3.2.1.2
-- 1.3.6.1.4.1.17409.1.3.2.1.2
-- 1.3.6.1.4.1.17409.1.3.2.1.2
-- 1.3.6.1.4.1.17409.1.3.2.1.2
-- 1.3.6.1.4.1.17409.1.3.2.1.2
-- 1.3.6.1.4.1.17409.1.3.2.1.2
-- 1.3.6.1.4.1.17409.1.3.2.1.2
-- 1.3.6.1.4.1.17409.1.3.2.1.2
		-- 1.3.6.1.4.1.17409.1.3.2.1.2
		commonBackoffParams OBJECT IDENTIFIER ::= { commonMACGroup 2 }

		
--          ************************
-- *   backoff算法相关参数
-- ************************
-- 1.3.6.1.4.1.1.1.3.2.1.2.1
-- 1.3.6.1.4.1.17409.1.3.2.1.2.1
-- 1.3.6.1.4.1.17409.1.3.2.1.2.1
-- 1.3.6.1.4.1.17409.1.3.2.1.2.1
-- 1.3.6.1.4.1.17409.1.3.2.1.2.1
-- 1.3.6.1.4.1.17409.1.3.2.1.2.1
-- 1.3.6.1.4.1.17409.1.3.2.1.2.1
-- 1.3.6.1.4.1.17409.1.3.2.1.2.1
		-- 1.3.6.1.4.1.17409.1.3.2.1.2.1
		commonBackoffPeriod OBJECT-TYPE
			SYNTAX INTEGER (0..16383)
			MAX-ACCESS read-write
			STATUS current
			DESCRIPTION
				"Backoff算法的基准时间（ms），初始化缺省值为6ms。
				此对象的值应保存在非易失性存储器中。"
			::= { commonBackoffParams 1 }

		
--         1.3.6.1.4.1.1.1.3.2.1.2.2
-- 1.3.6.1.4.1.17409.1.3.2.1.2.2
-- 1.3.6.1.4.1.17409.1.3.2.1.2.2
-- 1.3.6.1.4.1.17409.1.3.2.1.2.2
-- 1.3.6.1.4.1.17409.1.3.2.1.2.2
-- 1.3.6.1.4.1.17409.1.3.2.1.2.2
-- 1.3.6.1.4.1.17409.1.3.2.1.2.2
-- 1.3.6.1.4.1.17409.1.3.2.1.2.2
		-- 1.3.6.1.4.1.17409.1.3.2.1.2.2
		commonACKTimeoutWindow OBJECT-TYPE
			SYNTAX INTEGER (0..255)
			MAX-ACCESS read-write
			STATUS current
			DESCRIPTION
				"NE等待HE发送ACK响应的超时时间（ms），初始化缺省值为19ms。
				此对象的值应保存在非易失性存储器中。"
			::= { commonBackoffParams 2 }

		
--         1.3.6.1.4.1.1.1.3.2.1.2.3
-- 1.3.6.1.4.1.17409.1.3.2.1.2.3
-- 1.3.6.1.4.1.17409.1.3.2.1.2.3
-- 1.3.6.1.4.1.17409.1.3.2.1.2.3
-- 1.3.6.1.4.1.17409.1.3.2.1.2.3
-- 1.3.6.1.4.1.17409.1.3.2.1.2.3
-- 1.3.6.1.4.1.17409.1.3.2.1.2.3
-- 1.3.6.1.4.1.17409.1.3.2.1.2.3
		-- 1.3.6.1.4.1.17409.1.3.2.1.2.3
		commonMaximumMACLayerRetries OBJECT-TYPE
			SYNTAX INTEGER (0..255)
			MAX-ACCESS read-write
			STATUS current
			DESCRIPTION
				"NE发送数据包的最大重试次数。初始化缺省值为16。 
				此对象的值应保存在非易失性存储器中。"
			::= { commonBackoffParams 3 }

		
--         1.3.6.1.4.1.1.1.3.2.1.2.4
-- 1.3.6.1.4.1.17409.1.3.2.1.2.4
-- 1.3.6.1.4.1.17409.1.3.2.1.2.4
-- 1.3.6.1.4.1.17409.1.3.2.1.2.4
-- 1.3.6.1.4.1.17409.1.3.2.1.2.4
-- 1.3.6.1.4.1.17409.1.3.2.1.2.4
-- 1.3.6.1.4.1.17409.1.3.2.1.2.4
-- 1.3.6.1.4.1.17409.1.3.2.1.2.4
		-- 1.3.6.1.4.1.17409.1.3.2.1.2.4
		commonMaxPayloadSize OBJECT-TYPE
			SYNTAX Integer32
			MAX-ACCESS read-only
			STATUS current
			DESCRIPTION
				"上下行信道数据包所支持的最大有效载荷（payload）的长度。"
			::= { commonBackoffParams 4 }

		
--         1.3.6.1.4.1.1.1.3.2.1.2.5
-- 1.3.6.1.4.1.17409.1.3.2.1.2.5
-- 1.3.6.1.4.1.17409.1.3.2.1.2.5
-- 1.3.6.1.4.1.17409.1.3.2.1.2.5
-- 1.3.6.1.4.1.17409.1.3.2.1.2.5
-- 1.3.6.1.4.1.17409.1.3.2.1.2.5
-- 1.3.6.1.4.1.17409.1.3.2.1.2.5
-- 1.3.6.1.4.1.17409.1.3.2.1.2.5
		-- 1.3.6.1.4.1.17409.1.3.2.1.2.5
		commonBackoffMinimumExponent OBJECT-TYPE
			SYNTAX INTEGER (0..15)
			MAX-ACCESS read-write
			STATUS current
			DESCRIPTION
				"本标准正文中MAC层规范定义的backoff算法的最小指数值，缺省值为6。
				此值不得大于commonBackoffMaximumValue值。
				此对象的值应保存在非易失性存储器中。"
			::= { commonBackoffParams 5 }

		
--         1.3.6.1.4.1.1.1.3.2.1.2.6
-- 1.3.6.1.4.1.17409.1.3.2.1.2.6
-- 1.3.6.1.4.1.17409.1.3.2.1.2.6
-- 1.3.6.1.4.1.17409.1.3.2.1.2.6
-- 1.3.6.1.4.1.17409.1.3.2.1.2.6
-- 1.3.6.1.4.1.17409.1.3.2.1.2.6
-- 1.3.6.1.4.1.17409.1.3.2.1.2.6
-- 1.3.6.1.4.1.17409.1.3.2.1.2.6
		-- 1.3.6.1.4.1.17409.1.3.2.1.2.6
		commonBackoffMaximumExponent OBJECT-TYPE
			SYNTAX INTEGER (0..15)
			MAX-ACCESS read-write
			STATUS current
			DESCRIPTION
				"本标准正文中MAC层规范定义的backoff算法的最大指数值，缺省值为15。
				此值不得小于commonBackoffMinimum值。
				此对象的值应保存在非易失性存储器中。"
			::= { commonBackoffParams 6 }

		
--         1.3.6.1.4.1.1.1.3.2.1.3
-- 1.3.6.1.4.1.17409.1.3.2.1.3
-- 1.3.6.1.4.1.17409.1.3.2.1.3
-- 1.3.6.1.4.1.17409.1.3.2.1.3
-- 1.3.6.1.4.1.17409.1.3.2.1.3
-- 1.3.6.1.4.1.17409.1.3.2.1.3
-- 1.3.6.1.4.1.17409.1.3.2.1.3
-- 1.3.6.1.4.1.17409.1.3.2.1.3
		-- 1.3.6.1.4.1.17409.1.3.2.1.3
		commonMacStats OBJECT IDENTIFIER ::= { commonMACGroup 3 }

		
--          ******************
-- *   MAC层通信统计
-- ******************
-- 1.3.6.1.4.1.1.1.3.2.1.3.1
-- 1.3.6.1.4.1.17409.1.3.2.1.3.1
-- 1.3.6.1.4.1.17409.1.3.2.1.3.1
-- 1.3.6.1.4.1.17409.1.3.2.1.3.1
-- 1.3.6.1.4.1.17409.1.3.2.1.3.1
-- 1.3.6.1.4.1.17409.1.3.2.1.3.1
-- 1.3.6.1.4.1.17409.1.3.2.1.3.1
-- 1.3.6.1.4.1.17409.1.3.2.1.3.1
		-- 1.3.6.1.4.1.17409.1.3.2.1.3.1
		commonForwardPathLOSEvents OBJECT-TYPE
			SYNTAX Counter32
			MAX-ACCESS read-write
			STATUS optional
			DESCRIPTION
				"下行信道LOS发生数目，复位为0。"
			::= { commonMacStats 1 }

		
--         1.3.6.1.4.1.1.1.3.2.1.3.2
-- 1.3.6.1.4.1.17409.1.3.2.1.3.2
-- 1.3.6.1.4.1.17409.1.3.2.1.3.2
-- 1.3.6.1.4.1.17409.1.3.2.1.3.2
-- 1.3.6.1.4.1.17409.1.3.2.1.3.2
-- 1.3.6.1.4.1.17409.1.3.2.1.3.2
-- 1.3.6.1.4.1.17409.1.3.2.1.3.2
-- 1.3.6.1.4.1.17409.1.3.2.1.3.2
		-- 1.3.6.1.4.1.17409.1.3.2.1.3.2
		commonForwardPathFramingErrors OBJECT-TYPE
			SYNTAX Counter32
			MAX-ACCESS read-write
			STATUS optional
			DESCRIPTION
				"下行信道帧错误数目，复位为0。"
			::= { commonMacStats 2 }

		
--         1.3.6.1.4.1.1.1.3.2.1.3.3
-- 1.3.6.1.4.1.17409.1.3.2.1.3.3
-- 1.3.6.1.4.1.17409.1.3.2.1.3.3
-- 1.3.6.1.4.1.17409.1.3.2.1.3.3
-- 1.3.6.1.4.1.17409.1.3.2.1.3.3
-- 1.3.6.1.4.1.17409.1.3.2.1.3.3
-- 1.3.6.1.4.1.17409.1.3.2.1.3.3
-- 1.3.6.1.4.1.17409.1.3.2.1.3.3
		-- 1.3.6.1.4.1.17409.1.3.2.1.3.3
		commonForwardPathCRCErrors OBJECT-TYPE
			SYNTAX Counter32
			MAX-ACCESS read-write
			STATUS optional
			DESCRIPTION
				"下行CRC校验错误数目，复位为0。"
			::= { commonMacStats 3 }

		
--         1.3.6.1.4.1.1.1.3.2.1.3.4
-- 1.3.6.1.4.1.17409.1.3.2.1.3.4
-- 1.3.6.1.4.1.17409.1.3.2.1.3.4
-- 1.3.6.1.4.1.17409.1.3.2.1.3.4
-- 1.3.6.1.4.1.17409.1.3.2.1.3.4
-- 1.3.6.1.4.1.17409.1.3.2.1.3.4
-- 1.3.6.1.4.1.17409.1.3.2.1.3.4
-- 1.3.6.1.4.1.17409.1.3.2.1.3.4
		-- 1.3.6.1.4.1.17409.1.3.2.1.3.4
		commonInvalidMacCmds OBJECT-TYPE
			SYNTAX Counter32
			MAX-ACCESS read-write
			STATUS optional
			DESCRIPTION
				"无效的MAC层命令错误数目，复位为0。"
			::= { commonMacStats 4 }

		
--         1.3.6.1.4.1.1.1.3.2.1.3.5
-- 1.3.6.1.4.1.17409.1.3.2.1.3.5
-- 1.3.6.1.4.1.17409.1.3.2.1.3.5
-- 1.3.6.1.4.1.17409.1.3.2.1.3.5
-- 1.3.6.1.4.1.17409.1.3.2.1.3.5
-- 1.3.6.1.4.1.17409.1.3.2.1.3.5
-- 1.3.6.1.4.1.17409.1.3.2.1.3.5
-- 1.3.6.1.4.1.17409.1.3.2.1.3.5
		-- 1.3.6.1.4.1.17409.1.3.2.1.3.5
		commonBackwardPathCollisionTimes OBJECT-TYPE
			SYNTAX Counter32
			MAX-ACCESS read-write
			STATUS optional
			DESCRIPTION
				"上行数据包碰撞次数，复位为0。"
			::= { commonMacStats 5 }

		
--         1.3.6.1.4.1.1.1.3.2.2
-- 1.3.6.1.4.1.17409.1.3.2.2
-- 1.3.6.1.4.1.17409.1.3.2.2
-- 1.3.6.1.4.1.17409.1.3.2.2
-- 1.3.6.1.4.1.17409.1.3.2.2
-- 1.3.6.1.4.1.17409.1.3.2.2
-- 1.3.6.1.4.1.17409.1.3.2.2
-- 1.3.6.1.4.1.17409.1.3.2.2
		-- 1.3.6.1.4.1.17409.1.3.2.2
		commonRfGroup OBJECT IDENTIFIER ::= { commonAdminUseRf 2 }

		
--          *************
-- *   RF接口组
-- *************
-- 1.3.6.1.4.1.1.1.3.2.2.1
-- 1.3.6.1.4.1.17409.1.3.2.2.1
-- 1.3.6.1.4.1.17409.1.3.2.2.1
-- 1.3.6.1.4.1.17409.1.3.2.2.1
-- 1.3.6.1.4.1.17409.1.3.2.2.1
-- 1.3.6.1.4.1.17409.1.3.2.2.1
-- 1.3.6.1.4.1.17409.1.3.2.2.1
-- 1.3.6.1.4.1.17409.1.3.2.2.1
		-- 1.3.6.1.4.1.17409.1.3.2.2.1
		commonReturnPathFrequency OBJECT-TYPE
			SYNTAX INTEGER (0..1000000000)
			MAX-ACCESS read-only
			STATUS current
			DESCRIPTION
				"上行信道频率，单位为Hz。
				此对象的值应保存在非易失性存储器中。"
			::= { commonRfGroup 1 }

		
--         1.3.6.1.4.1.1.1.3.2.2.2
-- 1.3.6.1.4.1.17409.1.3.2.2.2
-- 1.3.6.1.4.1.17409.1.3.2.2.2
-- 1.3.6.1.4.1.17409.1.3.2.2.2
-- 1.3.6.1.4.1.17409.1.3.2.2.2
-- 1.3.6.1.4.1.17409.1.3.2.2.2
-- 1.3.6.1.4.1.17409.1.3.2.2.2
-- 1.3.6.1.4.1.17409.1.3.2.2.2
		-- 1.3.6.1.4.1.17409.1.3.2.2.2
		commonForwardPathFrequency OBJECT-TYPE
			SYNTAX INTEGER (0..1000000000)
			MAX-ACCESS read-only
			STATUS current
			DESCRIPTION
				"下行信道频率，单位为Hz。
				此对象的值应保存在非易失性存储器中。"
			::= { commonRfGroup 2 }

		
--         1.3.6.1.4.1.1.1.3.2.2.3
-- 1.3.6.1.4.1.17409.1.3.2.2.3
-- 1.3.6.1.4.1.17409.1.3.2.2.3
-- 1.3.6.1.4.1.17409.1.3.2.2.3
-- 1.3.6.1.4.1.17409.1.3.2.2.3
-- 1.3.6.1.4.1.17409.1.3.2.2.3
-- 1.3.6.1.4.1.17409.1.3.2.2.3
-- 1.3.6.1.4.1.17409.1.3.2.2.3
		-- 1.3.6.1.4.1.17409.1.3.2.2.3
		commonProvisionedReturnPowerLevel OBJECT-TYPE
			SYNTAX INTEGER (0..127)
			MAX-ACCESS read-write
			STATUS current
			DESCRIPTION
				"上行信道功率电平，单位为dBuV。
				内部使用时此值将被舍入到最接近的支持值。读此对象时返回实际值而不是舍入值。
				此对象的值应保存在非易失性存储器中。"
			::= { commonRfGroup 3 }

		
--         1.3.6.1.4.1.1.1.3.2.2.4
-- 1.3.6.1.4.1.17409.1.3.2.2.4
-- 1.3.6.1.4.1.17409.1.3.2.2.4
-- 1.3.6.1.4.1.17409.1.3.2.2.4
-- 1.3.6.1.4.1.17409.1.3.2.2.4
-- 1.3.6.1.4.1.17409.1.3.2.2.4
-- 1.3.6.1.4.1.17409.1.3.2.2.4
-- 1.3.6.1.4.1.17409.1.3.2.2.4
		-- 1.3.6.1.4.1.17409.1.3.2.2.4
		commonForwardPathReceiveLevel OBJECT-TYPE
			SYNTAX INTEGER (0..127)
			MAX-ACCESS read-only
			STATUS optional
			DESCRIPTION
				"下行信道接收功率电平，单位为dBuV。"
			::= { commonRfGroup 4 }

		
--         1.3.6.1.4.1.1.1.3.2.2.5
-- 1.3.6.1.4.1.17409.1.3.2.2.5
-- 1.3.6.1.4.1.17409.1.3.2.2.5
-- 1.3.6.1.4.1.17409.1.3.2.2.5
-- 1.3.6.1.4.1.17409.1.3.2.2.5
-- 1.3.6.1.4.1.17409.1.3.2.2.5
-- 1.3.6.1.4.1.17409.1.3.2.2.5
-- 1.3.6.1.4.1.17409.1.3.2.2.5
		-- 1.3.6.1.4.1.17409.1.3.2.2.5
		commonMaxReturnPower OBJECT-TYPE
			SYNTAX INTEGER (0..127)
			MAX-ACCESS read-write
			STATUS current
			DESCRIPTION
				"最大上行信道功率电平，单位为dBuV。
				此对象的值应保存在非易失性存储器中。"
			::= { commonRfGroup 5 }

		
--         1.3.6.1.4.1.1.1.3.3
-- 1.3.6.1.4.1.17409.1.3.3
-- 1.3.6.1.4.1.17409.1.3.3
-- 1.3.6.1.4.1.17409.1.3.3
-- 1.3.6.1.4.1.17409.1.3.3
-- 1.3.6.1.4.1.17409.1.3.3
-- 1.3.6.1.4.1.17409.1.3.3
-- 1.3.6.1.4.1.17409.1.3.3
		-- 1.3.6.1.4.1.17409.1.3.3
		commonAdminUseEthernet OBJECT IDENTIFIER ::= { commonIdent 3 }

		
--         1.3.6.1.4.1.1.1.3.3.1
-- 1.3.6.1.4.1.17409.1.3.3.1
-- 1.3.6.1.4.1.17409.1.3.3.1
-- 1.3.6.1.4.1.17409.1.3.3.1
-- 1.3.6.1.4.1.17409.1.3.3.1
-- 1.3.6.1.4.1.17409.1.3.3.1
-- 1.3.6.1.4.1.17409.1.3.3.1
-- 1.3.6.1.4.1.17409.1.3.3.1
		-- 1.3.6.1.4.1.17409.1.3.3.1
		commonAgentGroup OBJECT IDENTIFIER ::= { commonAdminUseEthernet 1 }

		
--          ************
-- *代理管理组
-- ************
-- 1.3.6.1.4.1.1.1.3.3.1.1
-- 1.3.6.1.4.1.17409.1.3.3.1.1
-- 1.3.6.1.4.1.17409.1.3.3.1.1
-- 1.3.6.1.4.1.17409.1.3.3.1.1
-- 1.3.6.1.4.1.17409.1.3.3.1.1
-- 1.3.6.1.4.1.17409.1.3.3.1.1
-- 1.3.6.1.4.1.17409.1.3.3.1.1
-- 1.3.6.1.4.1.17409.1.3.3.1.1
		-- 1.3.6.1.4.1.17409.1.3.3.1.1
		commonAgentBootWay OBJECT-TYPE
			SYNTAX INTEGER
				{
				bootDefault(1),
				bootBOOTP(2),
				bootTFTP(3)
				}
			MAX-ACCESS read-write
			STATUS current
			DESCRIPTION
				"代理启动方法"
			::= { commonAgentGroup 1 }

		
--         1.3.6.1.4.1.1.1.3.3.1.2
-- 1.3.6.1.4.1.17409.1.3.3.1.2
-- 1.3.6.1.4.1.17409.1.3.3.1.2
-- 1.3.6.1.4.1.17409.1.3.3.1.2
-- 1.3.6.1.4.1.17409.1.3.3.1.2
-- 1.3.6.1.4.1.17409.1.3.3.1.2
-- 1.3.6.1.4.1.17409.1.3.3.1.2
-- 1.3.6.1.4.1.17409.1.3.3.1.2
		-- 1.3.6.1.4.1.17409.1.3.3.1.2
		commonAgentReset OBJECT-TYPE
			SYNTAX INTEGER { reset(1) }
			MAX-ACCESS read-write
			STATUS current
			DESCRIPTION
				"代理重启动，写入'1'将使代理重新启动，写入其它值将不起作用。读此对象时返回值'1'，对代理无影响。"
			::= { commonAgentGroup 2 }

		
--         1.3.6.1.4.1.1.1.3.3.1.3
-- 1.3.6.1.4.1.17409.1.3.3.1.3
-- 1.3.6.1.4.1.17409.1.3.3.1.3
-- 1.3.6.1.4.1.17409.1.3.3.1.3
-- 1.3.6.1.4.1.17409.1.3.3.1.3
-- 1.3.6.1.4.1.17409.1.3.3.1.3
-- 1.3.6.1.4.1.17409.1.3.3.1.3
-- 1.3.6.1.4.1.17409.1.3.3.1.3
		-- 1.3.6.1.4.1.17409.1.3.3.1.3
		commonAgentMaxTraps OBJECT-TYPE
			SYNTAX Integer32
			MAX-ACCESS read-write
			STATUS current
			DESCRIPTION
				"代理检测到告警时向管理机发送TRAP的最大次数，0表示采用厂商的预设缺省值。"
			::= { commonAgentGroup 3 }

		
--         1.3.6.1.4.1.1.1.3.3.1.4
-- 1.3.6.1.4.1.17409.1.3.3.1.4
-- 1.3.6.1.4.1.17409.1.3.3.1.4
-- 1.3.6.1.4.1.17409.1.3.3.1.4
-- 1.3.6.1.4.1.17409.1.3.3.1.4
-- 1.3.6.1.4.1.17409.1.3.3.1.4
-- 1.3.6.1.4.1.17409.1.3.3.1.4
-- 1.3.6.1.4.1.17409.1.3.3.1.4
		-- 1.3.6.1.4.1.17409.1.3.3.1.4
		commonAgentTrapMinInterval OBJECT-TYPE
			SYNTAX Integer32
			MAX-ACCESS read-write
			STATUS current
			DESCRIPTION
				"代理发送TRAP的最小间隔，单位为s。"
			::= { commonAgentGroup 4 }

		
--         1.3.6.1.4.1.1.1.3.3.1.5
-- 1.3.6.1.4.1.17409.1.3.3.1.5
-- 1.3.6.1.4.1.17409.1.3.3.1.5
-- 1.3.6.1.4.1.17409.1.3.3.1.5
-- 1.3.6.1.4.1.17409.1.3.3.1.5
-- 1.3.6.1.4.1.17409.1.3.3.1.5
-- 1.3.6.1.4.1.17409.1.3.3.1.5
-- 1.3.6.1.4.1.17409.1.3.3.1.5
		-- 1.3.6.1.4.1.17409.1.3.3.1.5
		commonAgentTrapMaxInterval OBJECT-TYPE
			SYNTAX Integer32
			MAX-ACCESS read-write
			STATUS current
			DESCRIPTION
				"代理发送TRAP的最大间隔，单位为s。"
			::= { commonAgentGroup 5 }

		
--         1.3.6.1.4.1.1.1.3.3.1.6
-- 1.3.6.1.4.1.17409.1.3.3.1.6
-- 1.3.6.1.4.1.17409.1.3.3.1.6
-- 1.3.6.1.4.1.17409.1.3.3.1.6
-- 1.3.6.1.4.1.17409.1.3.3.1.6
-- 1.3.6.1.4.1.17409.1.3.3.1.6
-- 1.3.6.1.4.1.17409.1.3.3.1.6
-- 1.3.6.1.4.1.17409.1.3.3.1.6
		-- 1.3.6.1.4.1.17409.1.3.3.1.6
		commonTrapAck OBJECT-TYPE
			SYNTAX OCTET STRING (SIZE (17..255))
			MAX-ACCESS read-write
			STATUS optional
			DESCRIPTION
				"该变量用于通知Snmp代理，它所发出的告警Trap信息管理主机已经收到，不用重发。该变量的内容和告警MIB中alarmLogInformation 相同。代理收到后通过分析alarmLogInformation 可以明确地知道管理主机应答的是哪一条告警Trap信息，从而停止该告警Trap信息的重发。"
			::= { commonAgentGroup 6 }

		
--         1.3.6.1.4.1.1.1.3.3.1.7
-- 1.3.6.1.4.1.17409.1.3.3.1.7
-- 1.3.6.1.4.1.17409.1.3.3.1.7
-- 1.3.6.1.4.1.17409.1.3.3.1.7
-- 1.3.6.1.4.1.17409.1.3.3.1.7
-- 1.3.6.1.4.1.17409.1.3.3.1.7
-- 1.3.6.1.4.1.17409.1.3.3.1.7
-- 1.3.6.1.4.1.17409.1.3.3.1.7
		-- 1.3.6.1.4.1.17409.1.3.3.1.7
		commonAgentTrapTable OBJECT-TYPE
			SYNTAX SEQUENCE OF CommonAgentTrapEntry
			MAX-ACCESS not-accessible
			STATUS current
			DESCRIPTION
				"代理TRAP信息表。"
			::= { commonAgentGroup 7 }

		
--         1.3.6.1.4.1.1.1.3.3.1.7.1
-- 1.3.6.1.4.1.17409.1.3.3.1.7.1
-- 1.3.6.1.4.1.17409.1.3.3.1.7.1
-- 1.3.6.1.4.1.17409.1.3.3.1.7.1
-- 1.3.6.1.4.1.17409.1.3.3.1.7.1
-- 1.3.6.1.4.1.17409.1.3.3.1.7.1
-- 1.3.6.1.4.1.17409.1.3.3.1.7.1
-- 1.3.6.1.4.1.17409.1.3.3.1.7.1
		-- 1.3.6.1.4.1.17409.1.3.3.1.7.1
		commonAgentTrapEntry OBJECT-TYPE
			SYNTAX CommonAgentTrapEntry
			MAX-ACCESS not-accessible
			STATUS current
			DESCRIPTION
				"代理TRAP信息表目。"
			INDEX { commonAgentTrapIndex }
			::= { commonAgentTrapTable 1 }

		
		CommonAgentTrapEntry ::=
			SEQUENCE { 
				commonAgentTrapIndex
					Integer32,
				commonAgentTrapIP
					IpAddress,
				commonAgentTrapCommunity
					DisplayString,
				commonAgentTrapStatus
					INTEGER
			 }

--         1.3.6.1.4.1.1.1.3.3.1.7.1.1
-- 1.3.6.1.4.1.17409.1.3.3.1.7.1.1
-- 1.3.6.1.4.1.17409.1.3.3.1.7.1.1
-- 1.3.6.1.4.1.17409.1.3.3.1.7.1.1
-- 1.3.6.1.4.1.17409.1.3.3.1.7.1.1
-- 1.3.6.1.4.1.17409.1.3.3.1.7.1.1
-- 1.3.6.1.4.1.17409.1.3.3.1.7.1.1
-- 1.3.6.1.4.1.17409.1.3.3.1.7.1.1
		-- 1.3.6.1.4.1.17409.1.3.3.1.7.1.1
		commonAgentTrapIndex OBJECT-TYPE
			SYNTAX Integer32
			MAX-ACCESS read-only
			STATUS current
			DESCRIPTION
				"TRAP表索引。"
			::= { commonAgentTrapEntry 1 }

		
--         1.3.6.1.4.1.1.1.3.3.1.7.1.2
-- 1.3.6.1.4.1.17409.1.3.3.1.7.1.2
-- 1.3.6.1.4.1.17409.1.3.3.1.7.1.2
-- 1.3.6.1.4.1.17409.1.3.3.1.7.1.2
-- 1.3.6.1.4.1.17409.1.3.3.1.7.1.2
-- 1.3.6.1.4.1.17409.1.3.3.1.7.1.2
-- 1.3.6.1.4.1.17409.1.3.3.1.7.1.2
-- 1.3.6.1.4.1.17409.1.3.3.1.7.1.2
		-- 1.3.6.1.4.1.17409.1.3.3.1.7.1.2
		commonAgentTrapIP OBJECT-TYPE
			SYNTAX IpAddress
			MAX-ACCESS read-write
			STATUS current
			DESCRIPTION
				"发TRAP时目的主机的IP地址。"
			::= { commonAgentTrapEntry 2 }

		
--         1.3.6.1.4.1.1.1.3.3.1.7.1.3
-- 1.3.6.1.4.1.17409.1.3.3.1.7.1.3
-- 1.3.6.1.4.1.17409.1.3.3.1.7.1.3
-- 1.3.6.1.4.1.17409.1.3.3.1.7.1.3
-- 1.3.6.1.4.1.17409.1.3.3.1.7.1.3
-- 1.3.6.1.4.1.17409.1.3.3.1.7.1.3
-- 1.3.6.1.4.1.17409.1.3.3.1.7.1.3
-- 1.3.6.1.4.1.17409.1.3.3.1.7.1.3
		-- 1.3.6.1.4.1.17409.1.3.3.1.7.1.3
		commonAgentTrapCommunity OBJECT-TYPE
			SYNTAX DisplayString (SIZE (0..64))
			MAX-ACCESS read-write
			STATUS current
			DESCRIPTION
				"发送TRAP时的共同体字符串。"
			::= { commonAgentTrapEntry 3 }

		
--         1.3.6.1.4.1.1.1.3.3.1.7.1.4
-- 1.3.6.1.4.1.17409.1.3.3.1.7.1.4
-- 1.3.6.1.4.1.17409.1.3.3.1.7.1.4
-- 1.3.6.1.4.1.17409.1.3.3.1.7.1.4
-- 1.3.6.1.4.1.17409.1.3.3.1.7.1.4
-- 1.3.6.1.4.1.17409.1.3.3.1.7.1.4
-- 1.3.6.1.4.1.17409.1.3.3.1.7.1.4
-- 1.3.6.1.4.1.17409.1.3.3.1.7.1.4
		-- 1.3.6.1.4.1.17409.1.3.3.1.7.1.4
		commonAgentTrapStatus OBJECT-TYPE
			SYNTAX INTEGER
				{
				commonAgentTrapEnable(1),
				commonAgentTrapDisable(2)
				}
			MAX-ACCESS read-write
			STATUS current
			DESCRIPTION
				"表示该TRAP项是否启用。"
			::= { commonAgentTrapEntry 4 }

		
--         1.3.6.1.4.1.1.1.3.3.2
-- 1.3.6.1.4.1.17409.1.3.3.2
-- 1.3.6.1.4.1.17409.1.3.3.2
-- 1.3.6.1.4.1.17409.1.3.3.2
-- 1.3.6.1.4.1.17409.1.3.3.2
-- 1.3.6.1.4.1.17409.1.3.3.2
-- 1.3.6.1.4.1.17409.1.3.3.2
-- 1.3.6.1.4.1.17409.1.3.3.2
		-- 1.3.6.1.4.1.17409.1.3.3.2
		commonDeviceGroup OBJECT IDENTIFIER ::= { commonAdminUseEthernet 2 }

		
--          ***************
-- *   设备管理组
-- ***************
-- 1.3.6.1.4.1.1.1.3.3.2.1
-- 1.3.6.1.4.1.17409.1.3.3.2.1
-- 1.3.6.1.4.1.17409.1.3.3.2.1
-- 1.3.6.1.4.1.17409.1.3.3.2.1
-- 1.3.6.1.4.1.17409.1.3.3.2.1
-- 1.3.6.1.4.1.17409.1.3.3.2.1
-- 1.3.6.1.4.1.17409.1.3.3.2.1
-- 1.3.6.1.4.1.17409.1.3.3.2.1
		-- 1.3.6.1.4.1.17409.1.3.3.2.1
		commonDeviceNum OBJECT-TYPE
			SYNTAX Integer32
			MAX-ACCESS read-write
			STATUS current
			DESCRIPTION
				"表示该代理当前正在管理的设备数量。"
			::= { commonDeviceGroup 1 }

		
--         1.3.6.1.4.1.1.1.3.3.2.2
-- 1.3.6.1.4.1.17409.1.3.3.2.2
-- 1.3.6.1.4.1.17409.1.3.3.2.2
-- 1.3.6.1.4.1.17409.1.3.3.2.2
-- 1.3.6.1.4.1.17409.1.3.3.2.2
-- 1.3.6.1.4.1.17409.1.3.3.2.2
-- 1.3.6.1.4.1.17409.1.3.3.2.2
-- 1.3.6.1.4.1.17409.1.3.3.2.2
		-- 1.3.6.1.4.1.17409.1.3.3.2.2
		commonDeviceInfoTable OBJECT-TYPE
			SYNTAX SEQUENCE OF CommonDeviceInfoEntry
			MAX-ACCESS not-accessible
			STATUS current
			DESCRIPTION
				"代理当前正在管理的设备公共信息列表。"
			::= { commonDeviceGroup 2 }

		
--         1.3.6.1.4.1.1.1.3.3.2.2.1
-- 1.3.6.1.4.1.17409.1.3.3.2.2.1
-- 1.3.6.1.4.1.17409.1.3.3.2.2.1
-- 1.3.6.1.4.1.17409.1.3.3.2.2.1
-- 1.3.6.1.4.1.17409.1.3.3.2.2.1
-- 1.3.6.1.4.1.17409.1.3.3.2.2.1
-- 1.3.6.1.4.1.17409.1.3.3.2.2.1
-- 1.3.6.1.4.1.17409.1.3.3.2.2.1
		-- 1.3.6.1.4.1.17409.1.3.3.2.2.1
		commonDeviceInfoEntry OBJECT-TYPE
			SYNTAX CommonDeviceInfoEntry
			MAX-ACCESS not-accessible
			STATUS current
			DESCRIPTION
				"代理当前正在管理的设备公共信息列表表目。"
			INDEX { commonDeviceSlot }
			::= { commonDeviceInfoTable 1 }

		
		CommonDeviceInfoEntry ::=
			SEQUENCE { 
				commonDeviceSlot
					Integer32,
				commonDevicesID
					OCTET STRING,
				commonDeviceVendor
					DisplayString,
				commonDeviceModelNumber
					DisplayString,
				commonDeviceSerialNumber
					DisplayString,
				commonDeviceVendorInfo
					DisplayString,
				commonDeviceStatus
					OCTET STRING,
				commonDeviceReset
					INTEGER,
				commonDeviceAlarmDetectionControl
					INTEGER,
				commonDeviceMACAddress
					IpAddress,
				commonDeviceTamperStatus
					INTEGER,
				commonDeviceInternalTemperature
					INTEGER,
				commonDeviceResetCause
					INTEGER,
				commonDeviceCraftStatus
					INTEGER,
				commonDevicesOID
					OBJECT IDENTIFIER,
				commonDeviceAcct
					Counter32,
				commonDeviceName
					DisplayString,
				commonDeviceMFD
					DisplayString,
				commonDeviceFW
					DisplayString
			 }

--         1.3.6.1.4.1.1.1.3.3.2.2.1.1
-- 1.3.6.1.4.1.17409.1.3.3.2.2.1.1
-- 1.3.6.1.4.1.17409.1.3.3.2.2.1.1
-- 1.3.6.1.4.1.17409.1.3.3.2.2.1.1
-- 1.3.6.1.4.1.17409.1.3.3.2.2.1.1
-- 1.3.6.1.4.1.17409.1.3.3.2.2.1.1
-- 1.3.6.1.4.1.17409.1.3.3.2.2.1.1
-- 1.3.6.1.4.1.17409.1.3.3.2.2.1.1
		-- 1.3.6.1.4.1.17409.1.3.3.2.2.1.1
		commonDeviceSlot OBJECT-TYPE
			SYNTAX Integer32
			MAX-ACCESS read-only
			STATUS current
			DESCRIPTION
				"代理当前正在管理的设备公共信息列表的表索引。"
			::= { commonDeviceInfoEntry 1 }

		
--         1.3.6.1.4.1.1.1.3.3.2.2.1.2
-- 1.3.6.1.4.1.17409.1.3.3.2.2.1.2
-- 1.3.6.1.4.1.17409.1.3.3.2.2.1.2
-- 1.3.6.1.4.1.17409.1.3.3.2.2.1.2
-- 1.3.6.1.4.1.17409.1.3.3.2.2.1.2
-- 1.3.6.1.4.1.17409.1.3.3.2.2.1.2
-- 1.3.6.1.4.1.17409.1.3.3.2.2.1.2
-- 1.3.6.1.4.1.17409.1.3.3.2.2.1.2
		-- 1.3.6.1.4.1.17409.1.3.3.2.2.1.2
		commonDevicesID OBJECT-TYPE
			SYNTAX OCTET STRING (SIZE (0..40))
			MAX-ACCESS read-only
			STATUS current
			DESCRIPTION
				"厂商指定的设备的标识"
			::= { commonDeviceInfoEntry 2 }

		
--         1.3.6.1.4.1.1.1.3.3.2.2.1.3
-- 1.3.6.1.4.1.17409.1.3.3.2.2.1.3
-- 1.3.6.1.4.1.17409.1.3.3.2.2.1.3
-- 1.3.6.1.4.1.17409.1.3.3.2.2.1.3
-- 1.3.6.1.4.1.17409.1.3.3.2.2.1.3
-- 1.3.6.1.4.1.17409.1.3.3.2.2.1.3
-- 1.3.6.1.4.1.17409.1.3.3.2.2.1.3
-- 1.3.6.1.4.1.17409.1.3.3.2.2.1.3
		-- 1.3.6.1.4.1.17409.1.3.3.2.2.1.3
		commonDeviceVendor OBJECT-TYPE
			SYNTAX DisplayString (SIZE (0..255))
			MAX-ACCESS read-only
			STATUS current
			DESCRIPTION
				"设备生产厂家。"
			::= { commonDeviceInfoEntry 3 }

		
--         1.3.6.1.4.1.1.1.3.3.2.2.1.4
-- 1.3.6.1.4.1.17409.1.3.3.2.2.1.4
-- 1.3.6.1.4.1.17409.1.3.3.2.2.1.4
-- 1.3.6.1.4.1.17409.1.3.3.2.2.1.4
-- 1.3.6.1.4.1.17409.1.3.3.2.2.1.4
-- 1.3.6.1.4.1.17409.1.3.3.2.2.1.4
-- 1.3.6.1.4.1.17409.1.3.3.2.2.1.4
-- 1.3.6.1.4.1.17409.1.3.3.2.2.1.4
		-- 1.3.6.1.4.1.17409.1.3.3.2.2.1.4
		commonDeviceModelNumber OBJECT-TYPE
			SYNTAX DisplayString (SIZE (0..255))
			MAX-ACCESS read-only
			STATUS current
			DESCRIPTION
				"设备的型号。"
			::= { commonDeviceInfoEntry 4 }

		
--         1.3.6.1.4.1.1.1.3.3.2.2.1.5
-- 1.3.6.1.4.1.17409.1.3.3.2.2.1.5
-- 1.3.6.1.4.1.17409.1.3.3.2.2.1.5
-- 1.3.6.1.4.1.17409.1.3.3.2.2.1.5
-- 1.3.6.1.4.1.17409.1.3.3.2.2.1.5
-- 1.3.6.1.4.1.17409.1.3.3.2.2.1.5
-- 1.3.6.1.4.1.17409.1.3.3.2.2.1.5
-- 1.3.6.1.4.1.17409.1.3.3.2.2.1.5
		-- 1.3.6.1.4.1.17409.1.3.3.2.2.1.5
		commonDeviceSerialNumber OBJECT-TYPE
			SYNTAX DisplayString (SIZE (0..255))
			MAX-ACCESS read-only
			STATUS current
			DESCRIPTION
				"设备的串号。"
			::= { commonDeviceInfoEntry 5 }

		
--         1.3.6.1.4.1.1.1.3.3.2.2.1.6
-- 1.3.6.1.4.1.17409.1.3.3.2.2.1.6
-- 1.3.6.1.4.1.17409.1.3.3.2.2.1.6
-- 1.3.6.1.4.1.17409.1.3.3.2.2.1.6
-- 1.3.6.1.4.1.17409.1.3.3.2.2.1.6
-- 1.3.6.1.4.1.17409.1.3.3.2.2.1.6
-- 1.3.6.1.4.1.17409.1.3.3.2.2.1.6
-- 1.3.6.1.4.1.17409.1.3.3.2.2.1.6
		-- 1.3.6.1.4.1.17409.1.3.3.2.2.1.6
		commonDeviceVendorInfo OBJECT-TYPE
			SYNTAX DisplayString (SIZE (0..255))
			MAX-ACCESS read-only
			STATUS optional
			DESCRIPTION
				"设备供应商的其它特殊指定信息。"
			::= { commonDeviceInfoEntry 6 }

		
--         1.3.6.1.4.1.1.1.3.3.2.2.1.7
-- 1.3.6.1.4.1.17409.1.3.3.2.2.1.7
-- 1.3.6.1.4.1.17409.1.3.3.2.2.1.7
-- 1.3.6.1.4.1.17409.1.3.3.2.2.1.7
-- 1.3.6.1.4.1.17409.1.3.3.2.2.1.7
-- 1.3.6.1.4.1.17409.1.3.3.2.2.1.7
-- 1.3.6.1.4.1.17409.1.3.3.2.2.1.7
-- 1.3.6.1.4.1.17409.1.3.3.2.2.1.7
		-- 1.3.6.1.4.1.17409.1.3.3.2.2.1.7
		commonDeviceStatus OBJECT-TYPE
			SYNTAX OCTET STRING (SIZE (1))
			MAX-ACCESS read-only
			STATUS current
			DESCRIPTION
				"设备状态
				Bit 0: RSVD0
				Bit 1: RSVD1
				Bit 2: RSVD2
				Bit 3: MAJOR ALARMS
				Bit 4: MINOR ALARMS
				Bit 5: RSVD5
				Bit 6: RSVD6
				Bit 7: RSVD7"
			::= { commonDeviceInfoEntry 7 }

		
--         1.3.6.1.4.1.1.1.3.3.2.2.1.8
-- 1.3.6.1.4.1.17409.1.3.3.2.2.1.8
-- 1.3.6.1.4.1.17409.1.3.3.2.2.1.8
-- 1.3.6.1.4.1.17409.1.3.3.2.2.1.8
-- 1.3.6.1.4.1.17409.1.3.3.2.2.1.8
-- 1.3.6.1.4.1.17409.1.3.3.2.2.1.8
-- 1.3.6.1.4.1.17409.1.3.3.2.2.1.8
-- 1.3.6.1.4.1.17409.1.3.3.2.2.1.8
		-- 1.3.6.1.4.1.17409.1.3.3.2.2.1.8
		commonDeviceReset OBJECT-TYPE
			SYNTAX INTEGER { reset(1) }
			MAX-ACCESS read-write
			STATUS current
			DESCRIPTION
				"写入'1'将复位设备，写入其它值将不起作用。读此对象时返回值'1'，对设备无影响。"
			::= { commonDeviceInfoEntry 8 }

		
--         1.3.6.1.4.1.1.1.3.3.2.2.1.9
-- 1.3.6.1.4.1.17409.1.3.3.2.2.1.9
-- 1.3.6.1.4.1.17409.1.3.3.2.2.1.9
-- 1.3.6.1.4.1.17409.1.3.3.2.2.1.9
-- 1.3.6.1.4.1.17409.1.3.3.2.2.1.9
-- 1.3.6.1.4.1.17409.1.3.3.2.2.1.9
-- 1.3.6.1.4.1.17409.1.3.3.2.2.1.9
-- 1.3.6.1.4.1.17409.1.3.3.2.2.1.9
		-- 1.3.6.1.4.1.17409.1.3.3.2.2.1.9
		commonDeviceAlarmDetectionControl OBJECT-TYPE
			SYNTAX INTEGER
				{
				detectionDisabled(1),
				detectionEnabled(2),
				detectionEnabledAndRegenerate(3)
				}
			MAX-ACCESS read-write
			STATUS current
			DESCRIPTION
				"此对象用于控制设备的告警检测。"
			::= { commonDeviceInfoEntry 9 }

		
--         1.3.6.1.4.1.1.1.3.3.2.2.1.10
-- 1.3.6.1.4.1.17409.1.3.3.2.2.1.10
-- 1.3.6.1.4.1.17409.1.3.3.2.2.1.10
-- 1.3.6.1.4.1.17409.1.3.3.2.2.1.10
-- 1.3.6.1.4.1.17409.1.3.3.2.2.1.10
-- 1.3.6.1.4.1.17409.1.3.3.2.2.1.10
-- 1.3.6.1.4.1.17409.1.3.3.2.2.1.10
-- 1.3.6.1.4.1.17409.1.3.3.2.2.1.10
		-- 1.3.6.1.4.1.17409.1.3.3.2.2.1.10
		commonDeviceMACAddress OBJECT-TYPE
			SYNTAX IpAddress
			MAX-ACCESS read-only
			STATUS current
			DESCRIPTION
				"设备MAC地址。"
			::= { commonDeviceInfoEntry 10 }

		
--         1.3.6.1.4.1.1.1.3.3.2.2.1.11
-- 1.3.6.1.4.1.17409.1.3.3.2.2.1.11
-- 1.3.6.1.4.1.17409.1.3.3.2.2.1.11
-- 1.3.6.1.4.1.17409.1.3.3.2.2.1.11
-- 1.3.6.1.4.1.17409.1.3.3.2.2.1.11
-- 1.3.6.1.4.1.17409.1.3.3.2.2.1.11
-- 1.3.6.1.4.1.17409.1.3.3.2.2.1.11
-- 1.3.6.1.4.1.17409.1.3.3.2.2.1.11
		-- 1.3.6.1.4.1.17409.1.3.3.2.2.1.11
		commonDeviceTamperStatus OBJECT-TYPE
			SYNTAX INTEGER
				{
				intact(1),
				compromised(2)
				}
			MAX-ACCESS read-only
			STATUS optional
			DESCRIPTION
				"报告设备的安全开关(如盖子是否打开)状态，此对象要求在离散属性表中对应一个条目。intact表示正常，compromised表示告警。"
			::= { commonDeviceInfoEntry 11 }

		
--         1.3.6.1.4.1.1.1.3.3.2.2.1.12
-- 1.3.6.1.4.1.17409.1.3.3.2.2.1.12
-- 1.3.6.1.4.1.17409.1.3.3.2.2.1.12
-- 1.3.6.1.4.1.17409.1.3.3.2.2.1.12
-- 1.3.6.1.4.1.17409.1.3.3.2.2.1.12
-- 1.3.6.1.4.1.17409.1.3.3.2.2.1.12
-- 1.3.6.1.4.1.17409.1.3.3.2.2.1.12
-- 1.3.6.1.4.1.17409.1.3.3.2.2.1.12
		-- 1.3.6.1.4.1.17409.1.3.3.2.2.1.12
		commonDeviceInternalTemperature OBJECT-TYPE
			SYNTAX INTEGER (-128..127)
			MAX-ACCESS read-only
			STATUS optional
			DESCRIPTION
				"设备的室（机）内温度，单位为摄氏度。此对象要求在属性表中对应一个条目。"
			::= { commonDeviceInfoEntry 12 }

		
--         1.3.6.1.4.1.1.1.3.3.2.2.1.13
-- 1.3.6.1.4.1.17409.1.3.3.2.2.1.13
-- 1.3.6.1.4.1.17409.1.3.3.2.2.1.13
-- 1.3.6.1.4.1.17409.1.3.3.2.2.1.13
-- 1.3.6.1.4.1.17409.1.3.3.2.2.1.13
-- 1.3.6.1.4.1.17409.1.3.3.2.2.1.13
-- 1.3.6.1.4.1.17409.1.3.3.2.2.1.13
-- 1.3.6.1.4.1.17409.1.3.3.2.2.1.13
		-- 1.3.6.1.4.1.17409.1.3.3.2.2.1.13
		commonDeviceResetCause OBJECT-TYPE
			SYNTAX INTEGER
				{
				other(1),
				powerup(2),
				command(3),
				watchdog(4),
				craft(5)
				}
			MAX-ACCESS read-only
			STATUS current
			DESCRIPTION
				"表示设备最近一次复位的原因。"
			::= { commonDeviceInfoEntry 13 }

		
--         1.3.6.1.4.1.1.1.3.3.2.2.1.14
-- 1.3.6.1.4.1.17409.1.3.3.2.2.1.14
-- 1.3.6.1.4.1.17409.1.3.3.2.2.1.14
-- 1.3.6.1.4.1.17409.1.3.3.2.2.1.14
-- 1.3.6.1.4.1.17409.1.3.3.2.2.1.14
-- 1.3.6.1.4.1.17409.1.3.3.2.2.1.14
-- 1.3.6.1.4.1.17409.1.3.3.2.2.1.14
-- 1.3.6.1.4.1.17409.1.3.3.2.2.1.14
		-- 1.3.6.1.4.1.17409.1.3.3.2.2.1.14
		commonDeviceCraftStatus OBJECT-TYPE
			SYNTAX INTEGER
				{
				disconnected(1),
				connected(2)
				}
			MAX-ACCESS read-only
			STATUS current
			DESCRIPTION
				"此对象表示设备本地接口（如RS232或RS485接口）的状态。"
			::= { commonDeviceInfoEntry 14 }

		
--         1.3.6.1.4.1.1.1.3.3.2.2.1.15
-- 1.3.6.1.4.1.17409.1.3.3.2.2.1.15
-- 1.3.6.1.4.1.17409.1.3.3.2.2.1.15
-- 1.3.6.1.4.1.17409.1.3.3.2.2.1.15
-- 1.3.6.1.4.1.17409.1.3.3.2.2.1.15
-- 1.3.6.1.4.1.17409.1.3.3.2.2.1.15
-- 1.3.6.1.4.1.17409.1.3.3.2.2.1.15
-- 1.3.6.1.4.1.17409.1.3.3.2.2.1.15
		-- 1.3.6.1.4.1.17409.1.3.3.2.2.1.15
		commonDevicesOID OBJECT-TYPE
			SYNTAX OBJECT IDENTIFIER
			MAX-ACCESS read-only
			STATUS current
			DESCRIPTION
				"目标标识符串，指向该设备的具体实现。"
			::= { commonDeviceInfoEntry 15 }

		
--         1.3.6.1.4.1.1.1.3.3.2.2.1.16
-- 1.3.6.1.4.1.17409.1.3.3.2.2.1.16
-- 1.3.6.1.4.1.17409.1.3.3.2.2.1.16
-- 1.3.6.1.4.1.17409.1.3.3.2.2.1.16
-- 1.3.6.1.4.1.17409.1.3.3.2.2.1.16
-- 1.3.6.1.4.1.17409.1.3.3.2.2.1.16
-- 1.3.6.1.4.1.17409.1.3.3.2.2.1.16
-- 1.3.6.1.4.1.17409.1.3.3.2.2.1.16
		-- 1.3.6.1.4.1.17409.1.3.3.2.2.1.16
		commonDeviceAcct OBJECT-TYPE
			SYNTAX Counter32
			MAX-ACCESS read-only
			STATUS optional
			DESCRIPTION
				"表示设备的累计工作时间，单位为s。"
			::= { commonDeviceInfoEntry 16 }

		
--         1.3.6.1.4.1.1.1.3.3.2.2.1.17
-- 1.3.6.1.4.1.17409.1.3.3.2.2.1.17
-- 1.3.6.1.4.1.17409.1.3.3.2.2.1.17
-- 1.3.6.1.4.1.17409.1.3.3.2.2.1.17
-- 1.3.6.1.4.1.17409.1.3.3.2.2.1.17
-- 1.3.6.1.4.1.17409.1.3.3.2.2.1.17
-- 1.3.6.1.4.1.17409.1.3.3.2.2.1.17
-- 1.3.6.1.4.1.17409.1.3.3.2.2.1.17
		-- 1.3.6.1.4.1.17409.1.3.3.2.2.1.17
		commonDeviceName OBJECT-TYPE
			SYNTAX DisplayString (SIZE (0..255))
			MAX-ACCESS read-only
			STATUS current
			DESCRIPTION
				"设备名称。"
			::= { commonDeviceInfoEntry 17 }

		
--         1.3.6.1.4.1.1.1.3.3.2.2.1.18
-- 1.3.6.1.4.1.17409.1.3.3.2.2.1.18
-- 1.3.6.1.4.1.17409.1.3.3.2.2.1.18
-- 1.3.6.1.4.1.17409.1.3.3.2.2.1.18
-- 1.3.6.1.4.1.17409.1.3.3.2.2.1.18
-- 1.3.6.1.4.1.17409.1.3.3.2.2.1.18
-- 1.3.6.1.4.1.17409.1.3.3.2.2.1.18
-- 1.3.6.1.4.1.17409.1.3.3.2.2.1.18
		-- 1.3.6.1.4.1.17409.1.3.3.2.2.1.18
		commonDeviceMFD OBJECT-TYPE
			SYNTAX DisplayString (SIZE (10))
			MAX-ACCESS read-only
			STATUS current
			DESCRIPTION
				"设备生产日期。"
			::= { commonDeviceInfoEntry 18 }

		
--         1.3.6.1.4.1.1.1.3.3.2.2.1.19
-- 1.3.6.1.4.1.17409.1.3.3.2.2.1.19
-- 1.3.6.1.4.1.17409.1.3.3.2.2.1.19
-- 1.3.6.1.4.1.17409.1.3.3.2.2.1.19
-- 1.3.6.1.4.1.17409.1.3.3.2.2.1.19
-- 1.3.6.1.4.1.17409.1.3.3.2.2.1.19
-- 1.3.6.1.4.1.17409.1.3.3.2.2.1.19
-- 1.3.6.1.4.1.17409.1.3.3.2.2.1.19
		-- 1.3.6.1.4.1.17409.1.3.3.2.2.1.19
		commonDeviceFW OBJECT-TYPE
			SYNTAX DisplayString (SIZE (0..255))
			MAX-ACCESS read-only
			STATUS current
			DESCRIPTION
				"设备固件信息。"
			::= { commonDeviceInfoEntry 19 }

		
--              DESCRIPTION
-- "公用(Common)MIB的分支节点标识。"
-- "见附录E。"
-- 1.3.6.1.4.1.1.1.4
-- 1.3.6.1.4.1.17409.1.4
-- 1.3.6.1.4.1.17409.1.4
-- 1.3.6.1.4.1.17409.1.4
-- 1.3.6.1.4.1.17409.1.4
-- 1.3.6.1.4.1.17409.1.4
-- 1.3.6.1.4.1.17409.1.4
-- 1.3.6.1.4.1.17409.1.4
		-- 1.3.6.1.4.1.17409.1.4
		tvmodIdent OBJECT IDENTIFIER ::= { nscrtvHFCemsTree 4 }

		
--         *********************************************************************************************
-- 模拟电视调制器MIB
-- *********************************************************************************************
-- 1.3.6.1.4.1.1.1.4.1
-- 1.3.6.1.4.1.17409.1.4.1
-- 1.3.6.1.4.1.17409.1.4.1
-- 1.3.6.1.4.1.17409.1.4.1
-- 1.3.6.1.4.1.17409.1.4.1
-- 1.3.6.1.4.1.17409.1.4.1
-- 1.3.6.1.4.1.17409.1.4.1
-- 1.3.6.1.4.1.17409.1.4.1
		-- 1.3.6.1.4.1.17409.1.4.1
		tvmodVendorOID OBJECT-TYPE
			SYNTAX OBJECT IDENTIFIER
			MAX-ACCESS read-only
			STATUS optional
			DESCRIPTION
				"此对象提供厂商对模拟电视调制器MIB的扩充。无扩充时此对象应指向模拟电视调制器节点tvmodIdent。"
			::= { tvmodIdent 1 }

		
--         1.3.6.1.4.1.1.1.4.2
-- 1.3.6.1.4.1.17409.1.4.2
-- 1.3.6.1.4.1.17409.1.4.2
-- 1.3.6.1.4.1.17409.1.4.2
-- 1.3.6.1.4.1.17409.1.4.2
-- 1.3.6.1.4.1.17409.1.4.2
-- 1.3.6.1.4.1.17409.1.4.2
-- 1.3.6.1.4.1.17409.1.4.2
		-- 1.3.6.1.4.1.17409.1.4.2
		tvmodOutputlevel OBJECT-TYPE
			SYNTAX INTEGER (0..255)
			MAX-ACCESS read-only
			STATUS current
			DESCRIPTION
				"输出电平，单位为dBuV，此对象要求在属性MIB中登记一个条目。"
			::= { tvmodIdent 2 }

		
--         1.3.6.1.4.1.1.1.4.3
-- 1.3.6.1.4.1.17409.1.4.3
-- 1.3.6.1.4.1.17409.1.4.3
-- 1.3.6.1.4.1.17409.1.4.3
-- 1.3.6.1.4.1.17409.1.4.3
-- 1.3.6.1.4.1.17409.1.4.3
-- 1.3.6.1.4.1.17409.1.4.3
-- 1.3.6.1.4.1.17409.1.4.3
		-- 1.3.6.1.4.1.17409.1.4.3
		tvmodOutputlevelAtt OBJECT-TYPE
			SYNTAX INTEGER (0..255)
			MAX-ACCESS read-write
			STATUS current
			DESCRIPTION
				"衰减量，单位为dB。"
			::= { tvmodIdent 3 }

		
--         1.3.6.1.4.1.1.1.4.4
-- 1.3.6.1.4.1.17409.1.4.4
-- 1.3.6.1.4.1.17409.1.4.4
-- 1.3.6.1.4.1.17409.1.4.4
-- 1.3.6.1.4.1.17409.1.4.4
-- 1.3.6.1.4.1.17409.1.4.4
-- 1.3.6.1.4.1.17409.1.4.4
-- 1.3.6.1.4.1.17409.1.4.4
		-- 1.3.6.1.4.1.17409.1.4.4
		tvmodAVPower-ratio OBJECT-TYPE
			SYNTAX INTEGER (-128..127)
			MAX-ACCESS read-write
			STATUS current
			DESCRIPTION
				"图象伴音功率比（A/V）,单位为dB。"
			::= { tvmodIdent 4 }

		
--         1.3.6.1.4.1.1.1.4.5
-- 1.3.6.1.4.1.17409.1.4.5
-- 1.3.6.1.4.1.17409.1.4.5
-- 1.3.6.1.4.1.17409.1.4.5
-- 1.3.6.1.4.1.17409.1.4.5
-- 1.3.6.1.4.1.17409.1.4.5
-- 1.3.6.1.4.1.17409.1.4.5
-- 1.3.6.1.4.1.17409.1.4.5
		-- 1.3.6.1.4.1.17409.1.4.5
		tvmodfreqdeviation OBJECT-TYPE
			SYNTAX INTEGER (0..255)
			MAX-ACCESS read-write
			STATUS current
			DESCRIPTION
				"频偏，单位为KHz。"
			::= { tvmodIdent 5 }

		
--         1.3.6.1.4.1.1.1.4.6
-- 1.3.6.1.4.1.17409.1.4.6
-- 1.3.6.1.4.1.17409.1.4.6
-- 1.3.6.1.4.1.17409.1.4.6
-- 1.3.6.1.4.1.17409.1.4.6
-- 1.3.6.1.4.1.17409.1.4.6
-- 1.3.6.1.4.1.17409.1.4.6
-- 1.3.6.1.4.1.17409.1.4.6
		-- 1.3.6.1.4.1.17409.1.4.6
		tvmodOperatingFreq OBJECT-TYPE
			SYNTAX Integer32
			MAX-ACCESS read-write
			STATUS current
			DESCRIPTION
				"输出频率,单位为Hz。"
			::= { tvmodIdent 6 }

		
--         1.3.6.1.4.1.1.1.4.7
-- 1.3.6.1.4.1.17409.1.4.7
-- 1.3.6.1.4.1.17409.1.4.7
-- 1.3.6.1.4.1.17409.1.4.7
-- 1.3.6.1.4.1.17409.1.4.7
-- 1.3.6.1.4.1.17409.1.4.7
-- 1.3.6.1.4.1.17409.1.4.7
-- 1.3.6.1.4.1.17409.1.4.7
		-- 1.3.6.1.4.1.17409.1.4.7
		tvmodModulatingDepth OBJECT-TYPE
			SYNTAX INTEGER (0..99)
			MAX-ACCESS read-write
			STATUS current
			DESCRIPTION
				"调制度,单位为1%,'0'表示：无调制。"
			::= { tvmodIdent 7 }

		
--         1.3.6.1.4.1.1.1.4.8
-- 1.3.6.1.4.1.17409.1.4.8
-- 1.3.6.1.4.1.17409.1.4.8
-- 1.3.6.1.4.1.17409.1.4.8
-- 1.3.6.1.4.1.17409.1.4.8
-- 1.3.6.1.4.1.17409.1.4.8
-- 1.3.6.1.4.1.17409.1.4.8
-- 1.3.6.1.4.1.17409.1.4.8
		-- 1.3.6.1.4.1.17409.1.4.8
		tvmodLockalarm OBJECT-TYPE
			SYNTAX INTEGER
				{
				normal(1),
				alarm(2)
				}
			MAX-ACCESS read-only
			STATUS current
			DESCRIPTION
				"锁相告警，'1'为正常，'2'为告警。此对象要求在属性MIB中登记一个条目。"
			::= { tvmodIdent 8 }

		
--          *****************
-- * 直流电源
-- *****************
-- 1.3.6.1.4.1.1.1.4.9
-- 1.3.6.1.4.1.17409.1.4.9
-- 1.3.6.1.4.1.17409.1.4.9
-- 1.3.6.1.4.1.17409.1.4.9
-- 1.3.6.1.4.1.17409.1.4.9
-- 1.3.6.1.4.1.17409.1.4.9
-- 1.3.6.1.4.1.17409.1.4.9
-- 1.3.6.1.4.1.17409.1.4.9
		-- 1.3.6.1.4.1.17409.1.4.9
		tvmodNumberDCPowerSupply OBJECT-TYPE
			SYNTAX INTEGER (0..16)
			MAX-ACCESS read-only
			STATUS current
			DESCRIPTION
				"内部直流电源的数目，'0'表示应答器设备不支持无此功能。"
			::= { tvmodIdent 9 }

		
--         1.3.6.1.4.1.1.1.4.10
-- 1.3.6.1.4.1.17409.1.4.10
-- 1.3.6.1.4.1.17409.1.4.10
-- 1.3.6.1.4.1.17409.1.4.10
-- 1.3.6.1.4.1.17409.1.4.10
-- 1.3.6.1.4.1.17409.1.4.10
-- 1.3.6.1.4.1.17409.1.4.10
-- 1.3.6.1.4.1.17409.1.4.10
		-- 1.3.6.1.4.1.17409.1.4.10
		tvmodDCPowerSupplymode OBJECT-TYPE
			SYNTAX INTEGER
				{
				loadsharing(1),
				switchedRedundant(2)
				}
			MAX-ACCESS read-only
			STATUS optional
			DESCRIPTION
				"直流供电电源工作模式。"
			::= { tvmodIdent 10 }

		
--         1.3.6.1.4.1.1.1.4.11
-- 1.3.6.1.4.1.17409.1.4.11
-- 1.3.6.1.4.1.17409.1.4.11
-- 1.3.6.1.4.1.17409.1.4.11
-- 1.3.6.1.4.1.17409.1.4.11
-- 1.3.6.1.4.1.17409.1.4.11
-- 1.3.6.1.4.1.17409.1.4.11
-- 1.3.6.1.4.1.17409.1.4.11
		-- 1.3.6.1.4.1.17409.1.4.11
		tvmodDCPowerTable OBJECT-TYPE
			SYNTAX SEQUENCE OF TvmodDCPowerEntry
			MAX-ACCESS not-accessible
			STATUS current
			DESCRIPTION
				"直流电源信息表。"
			::= { tvmodIdent 11 }

		
--         1.3.6.1.4.1.1.1.4.11.1
-- 1.3.6.1.4.1.17409.1.4.11.1
-- 1.3.6.1.4.1.17409.1.4.11.1
-- 1.3.6.1.4.1.17409.1.4.11.1
-- 1.3.6.1.4.1.17409.1.4.11.1
-- 1.3.6.1.4.1.17409.1.4.11.1
-- 1.3.6.1.4.1.17409.1.4.11.1
-- 1.3.6.1.4.1.17409.1.4.11.1
		-- 1.3.6.1.4.1.17409.1.4.11.1
		tvmodDCPowerEntry OBJECT-TYPE
			SYNTAX TvmodDCPowerEntry
			MAX-ACCESS not-accessible
			STATUS current
			DESCRIPTION
				"直流电源信息表目。"
			INDEX { tvmodDCPowerIndex }
			::= { tvmodDCPowerTable 1 }

		
		TvmodDCPowerEntry ::=
			SEQUENCE { 
				tvmodDCPowerIndex
					Integer32,
				tvmodDCPowerVoltage
					INTEGER,
				tvmodDCPowerCurrent
					INTEGER,
				tvmodDCPowerName
					DisplayString
			 }

--         1.3.6.1.4.1.1.1.4.11.1.1
-- 1.3.6.1.4.1.17409.1.4.11.1.1
-- 1.3.6.1.4.1.17409.1.4.11.1.1
-- 1.3.6.1.4.1.17409.1.4.11.1.1
-- 1.3.6.1.4.1.17409.1.4.11.1.1
-- 1.3.6.1.4.1.17409.1.4.11.1.1
-- 1.3.6.1.4.1.17409.1.4.11.1.1
-- 1.3.6.1.4.1.17409.1.4.11.1.1
		-- 1.3.6.1.4.1.17409.1.4.11.1.1
		tvmodDCPowerIndex OBJECT-TYPE
			SYNTAX Integer32
			MAX-ACCESS read-only
			STATUS current
			DESCRIPTION
				"直流电源索引。"
			::= { tvmodDCPowerEntry 1 }

		
--         1.3.6.1.4.1.1.1.4.11.1.2
-- 1.3.6.1.4.1.17409.1.4.11.1.2
-- 1.3.6.1.4.1.17409.1.4.11.1.2
-- 1.3.6.1.4.1.17409.1.4.11.1.2
-- 1.3.6.1.4.1.17409.1.4.11.1.2
-- 1.3.6.1.4.1.17409.1.4.11.1.2
-- 1.3.6.1.4.1.17409.1.4.11.1.2
-- 1.3.6.1.4.1.17409.1.4.11.1.2
		-- 1.3.6.1.4.1.17409.1.4.11.1.2
		tvmodDCPowerVoltage OBJECT-TYPE
			SYNTAX INTEGER (-32768..32767)
			MAX-ACCESS read-only
			STATUS current
			DESCRIPTION
				"直流电源电压，单位为0.1V。此对象要求在属性MIB中登记一个条目。"
			::= { tvmodDCPowerEntry 2 }

		
--         1.3.6.1.4.1.1.1.4.11.1.3
-- 1.3.6.1.4.1.17409.1.4.11.1.3
-- 1.3.6.1.4.1.17409.1.4.11.1.3
-- 1.3.6.1.4.1.17409.1.4.11.1.3
-- 1.3.6.1.4.1.17409.1.4.11.1.3
-- 1.3.6.1.4.1.17409.1.4.11.1.3
-- 1.3.6.1.4.1.17409.1.4.11.1.3
-- 1.3.6.1.4.1.17409.1.4.11.1.3
		-- 1.3.6.1.4.1.17409.1.4.11.1.3
		tvmodDCPowerCurrent OBJECT-TYPE
			SYNTAX INTEGER (0..65535)
			MAX-ACCESS read-only
			STATUS optional
			DESCRIPTION
				"电源的电流，单位为0.01A。此对象要求在属性MIB中登记一个条目。"
			::= { tvmodDCPowerEntry 3 }

		
--         1.3.6.1.4.1.1.1.4.11.1.4
-- 1.3.6.1.4.1.17409.1.4.11.1.4
-- 1.3.6.1.4.1.17409.1.4.11.1.4
-- 1.3.6.1.4.1.17409.1.4.11.1.4
-- 1.3.6.1.4.1.17409.1.4.11.1.4
-- 1.3.6.1.4.1.17409.1.4.11.1.4
-- 1.3.6.1.4.1.17409.1.4.11.1.4
-- 1.3.6.1.4.1.17409.1.4.11.1.4
		-- 1.3.6.1.4.1.17409.1.4.11.1.4
		tvmodDCPowerName OBJECT-TYPE
			SYNTAX DisplayString
			MAX-ACCESS read-only
			STATUS current
			DESCRIPTION
				"标明直流电源名称，例如：24V直流电源。
				此字段值由用户规定，至少应标明工作电压并将多个电源相互区分开。
				当此表中的对象产生告警时，此对象名称应放进hfcAlarmEvent陷阱的alarmText对象里。"
			::= { tvmodDCPowerEntry 4 }

		
--              DESCRIPTION
-- "模拟电视调制器(TV Modulator)MIB的分支节点标识。"
-- "见附录F。"
-- 1.3.6.1.4.1.1.1.5
-- 1.3.6.1.4.1.17409.1.5
-- 1.3.6.1.4.1.17409.1.5
-- 1.3.6.1.4.1.17409.1.5
-- 1.3.6.1.4.1.17409.1.5
-- 1.3.6.1.4.1.17409.1.5
-- 1.3.6.1.4.1.17409.1.5
-- 1.3.6.1.4.1.17409.1.5
		-- 1.3.6.1.4.1.17409.1.5
		qammodIdent OBJECT IDENTIFIER ::= { nscrtvHFCemsTree 5 }

		
--         **********************************************************************************************
-- QAM调制器MIB
-- **********************************************************************************************
-- 1.3.6.1.4.1.1.1.5.1
-- 1.3.6.1.4.1.17409.1.5.1
-- 1.3.6.1.4.1.17409.1.5.1
-- 1.3.6.1.4.1.17409.1.5.1
-- 1.3.6.1.4.1.17409.1.5.1
-- 1.3.6.1.4.1.17409.1.5.1
-- 1.3.6.1.4.1.17409.1.5.1
-- 1.3.6.1.4.1.17409.1.5.1
		-- 1.3.6.1.4.1.17409.1.5.1
		qamModVendorOID OBJECT-TYPE
			SYNTAX OBJECT IDENTIFIER
			MAX-ACCESS read-only
			STATUS optional
			DESCRIPTION
				"此对象提供厂商对QAM调制器MIB的扩充。无扩充时此对象应指向QAM调制器节点qammodIdent。"
			::= { qammodIdent 1 }

		
--         1.3.6.1.4.1.1.1.5.2
-- 1.3.6.1.4.1.17409.1.5.2
-- 1.3.6.1.4.1.17409.1.5.2
-- 1.3.6.1.4.1.17409.1.5.2
-- 1.3.6.1.4.1.17409.1.5.2
-- 1.3.6.1.4.1.17409.1.5.2
-- 1.3.6.1.4.1.17409.1.5.2
-- 1.3.6.1.4.1.17409.1.5.2
		-- 1.3.6.1.4.1.17409.1.5.2
		qamModmode OBJECT-TYPE
			SYNTAX INTEGER (1..6)
			MAX-ACCESS read-write
			STATUS current
			DESCRIPTION
				"QAM模式,包括16、32、64、128、256、预留,共6种。"
			::= { qammodIdent 2 }

		
--         1.3.6.1.4.1.1.1.5.3
-- 1.3.6.1.4.1.17409.1.5.3
-- 1.3.6.1.4.1.17409.1.5.3
-- 1.3.6.1.4.1.17409.1.5.3
-- 1.3.6.1.4.1.17409.1.5.3
-- 1.3.6.1.4.1.17409.1.5.3
-- 1.3.6.1.4.1.17409.1.5.3
-- 1.3.6.1.4.1.17409.1.5.3
		-- 1.3.6.1.4.1.17409.1.5.3
		qamModsymbolrate OBJECT-TYPE
			SYNTAX INTEGER (0..65535)
			MAX-ACCESS read-write
			STATUS current
			DESCRIPTION
				"符号率，正常范围为1150..7000，单位为ksym/s。"
			::= { qammodIdent 3 }

		
--         1.3.6.1.4.1.1.1.5.4
-- 1.3.6.1.4.1.17409.1.5.4
-- 1.3.6.1.4.1.17409.1.5.4
-- 1.3.6.1.4.1.17409.1.5.4
-- 1.3.6.1.4.1.17409.1.5.4
-- 1.3.6.1.4.1.17409.1.5.4
-- 1.3.6.1.4.1.17409.1.5.4
-- 1.3.6.1.4.1.17409.1.5.4
		-- 1.3.6.1.4.1.17409.1.5.4
		qamModRFfreq OBJECT-TYPE
			SYNTAX Integer32
			MAX-ACCESS read-write
			STATUS current
			DESCRIPTION
				"RF频率,单位为Hz。"
			::= { qammodIdent 4 }

		
--         1.3.6.1.4.1.1.1.5.5
-- 1.3.6.1.4.1.17409.1.5.5
-- 1.3.6.1.4.1.17409.1.5.5
-- 1.3.6.1.4.1.17409.1.5.5
-- 1.3.6.1.4.1.17409.1.5.5
-- 1.3.6.1.4.1.17409.1.5.5
-- 1.3.6.1.4.1.17409.1.5.5
-- 1.3.6.1.4.1.17409.1.5.5
		-- 1.3.6.1.4.1.17409.1.5.5
		qamModRFLevel OBJECT-TYPE
			SYNTAX Integer32
			MAX-ACCESS read-only
			STATUS optional
			DESCRIPTION
				"RF输出电平，单位为dBuV。此对象要求在属性MIB中登记一个条目。"
			::= { qammodIdent 5 }

		
--         1.3.6.1.4.1.1.1.5.6
-- 1.3.6.1.4.1.17409.1.5.6
-- 1.3.6.1.4.1.17409.1.5.6
-- 1.3.6.1.4.1.17409.1.5.6
-- 1.3.6.1.4.1.17409.1.5.6
-- 1.3.6.1.4.1.17409.1.5.6
-- 1.3.6.1.4.1.17409.1.5.6
-- 1.3.6.1.4.1.17409.1.5.6
		-- 1.3.6.1.4.1.17409.1.5.6
		qamModRFLevelatt OBJECT-TYPE
			SYNTAX Integer32
			MAX-ACCESS read-write
			STATUS optional
			DESCRIPTION
				"RF输出电平衰减量，单位为dB。"
			::= { qammodIdent 6 }

		
--         1.3.6.1.4.1.1.1.5.7
-- 1.3.6.1.4.1.17409.1.5.7
-- 1.3.6.1.4.1.17409.1.5.7
-- 1.3.6.1.4.1.17409.1.5.7
-- 1.3.6.1.4.1.17409.1.5.7
-- 1.3.6.1.4.1.17409.1.5.7
-- 1.3.6.1.4.1.17409.1.5.7
-- 1.3.6.1.4.1.17409.1.5.7
		-- 1.3.6.1.4.1.17409.1.5.7
		qamModInputInterface OBJECT-TYPE
			SYNTAX INTEGER
				{
				asi(1),
				spi(2),
				ds3(3),
				other(4)
				}
			MAX-ACCESS read-only
			STATUS current
			DESCRIPTION
				"输入接口类型有asi、spi、ds3和其它。"
			::= { qammodIdent 7 }

		
--         1.3.6.1.4.1.1.1.5.8
-- 1.3.6.1.4.1.17409.1.5.8
-- 1.3.6.1.4.1.17409.1.5.8
-- 1.3.6.1.4.1.17409.1.5.8
-- 1.3.6.1.4.1.17409.1.5.8
-- 1.3.6.1.4.1.17409.1.5.8
-- 1.3.6.1.4.1.17409.1.5.8
-- 1.3.6.1.4.1.17409.1.5.8
		-- 1.3.6.1.4.1.17409.1.5.8
		qamModstatus OBJECT-TYPE
			SYNTAX INTEGER
				{
				sync(1),
				noSync(2)
				}
			MAX-ACCESS read-only
			STATUS current
			DESCRIPTION
				"调制状态有'1'同步和'2'不同步两种。此对象要求在属性MIB中登记一个条目。"
			::= { qammodIdent 8 }

		
--          modify by feihuaxin     
-- qamModTSpacketlen OBJECT-TYPE
--      SYNTAX INTEGER {
-- bytes188 (1),
-- bytes204 (2)
--        }
--      ACCESS read-write
--      STATUS mandatory
--      DESCRIPTION
--           "输入TS流包长度，'1'表示188字节，'2'表示204字节。"
--      ::= { qammodIdent 9 }    
--  
--  *****************
--  * 直流电源
--  *****************
-- 1.3.6.1.4.1.1.1.5.9
-- 1.3.6.1.4.1.17409.1.5.9
-- 1.3.6.1.4.1.17409.1.5.9
-- 1.3.6.1.4.1.17409.1.5.9
-- 1.3.6.1.4.1.17409.1.5.9
-- 1.3.6.1.4.1.17409.1.5.9
-- 1.3.6.1.4.1.17409.1.5.9
-- 1.3.6.1.4.1.17409.1.5.9
		-- 1.3.6.1.4.1.17409.1.5.9
		qamModNumberDCPowerSupply OBJECT-TYPE
			SYNTAX INTEGER (0..16)
			MAX-ACCESS read-only
			STATUS current
			DESCRIPTION
				"内部直流电源的数目，'0'表示设备无此功能。"
			::= { qammodIdent 9 }

		
--         1.3.6.1.4.1.1.1.5.10
-- 1.3.6.1.4.1.17409.1.5.10
-- 1.3.6.1.4.1.17409.1.5.10
-- 1.3.6.1.4.1.17409.1.5.10
-- 1.3.6.1.4.1.17409.1.5.10
-- 1.3.6.1.4.1.17409.1.5.10
-- 1.3.6.1.4.1.17409.1.5.10
-- 1.3.6.1.4.1.17409.1.5.10
		-- 1.3.6.1.4.1.17409.1.5.10
		qamModDCPowerSupplyMode OBJECT-TYPE
			SYNTAX INTEGER
				{
				loadsharing(1),
				switchedRedundant(2),
				aloneSupply(3)
				}
			MAX-ACCESS read-only
			STATUS optional
			DESCRIPTION
				"供电电源工作模式。"
			::= { qammodIdent 10 }

		
--         1.3.6.1.4.1.1.1.5.11
-- 1.3.6.1.4.1.17409.1.5.11
-- 1.3.6.1.4.1.17409.1.5.11
-- 1.3.6.1.4.1.17409.1.5.11
-- 1.3.6.1.4.1.17409.1.5.11
-- 1.3.6.1.4.1.17409.1.5.11
-- 1.3.6.1.4.1.17409.1.5.11
-- 1.3.6.1.4.1.17409.1.5.11
		-- 1.3.6.1.4.1.17409.1.5.11
		qamModDCPowerTable OBJECT-TYPE
			SYNTAX SEQUENCE OF QamModDCPowerEntry
			MAX-ACCESS not-accessible
			STATUS current
			DESCRIPTION
				"直流电源信息表。"
			::= { qammodIdent 11 }

		
--         1.3.6.1.4.1.1.1.5.11.1
-- 1.3.6.1.4.1.17409.1.5.11.1
-- 1.3.6.1.4.1.17409.1.5.11.1
-- 1.3.6.1.4.1.17409.1.5.11.1
-- 1.3.6.1.4.1.17409.1.5.11.1
-- 1.3.6.1.4.1.17409.1.5.11.1
-- 1.3.6.1.4.1.17409.1.5.11.1
-- 1.3.6.1.4.1.17409.1.5.11.1
		-- 1.3.6.1.4.1.17409.1.5.11.1
		qamModDCPowerEntry OBJECT-TYPE
			SYNTAX QamModDCPowerEntry
			MAX-ACCESS not-accessible
			STATUS current
			DESCRIPTION
				"直流电源信息表目。"
			INDEX { qamModDCPowerIndex }
			::= { qamModDCPowerTable 1 }

		
		QamModDCPowerEntry ::=
			SEQUENCE { 
				qamModDCPowerIndex
					Integer32,
				qamModDCPowerVoltage
					INTEGER,
				qamModDCPowerCurrent
					INTEGER,
				qamModDCPowerName
					DisplayString
			 }

--         1.3.6.1.4.1.1.1.5.11.1.1
-- 1.3.6.1.4.1.17409.1.5.11.1.1
-- 1.3.6.1.4.1.17409.1.5.11.1.1
-- 1.3.6.1.4.1.17409.1.5.11.1.1
-- 1.3.6.1.4.1.17409.1.5.11.1.1
-- 1.3.6.1.4.1.17409.1.5.11.1.1
-- 1.3.6.1.4.1.17409.1.5.11.1.1
-- 1.3.6.1.4.1.17409.1.5.11.1.1
		-- 1.3.6.1.4.1.17409.1.5.11.1.1
		qamModDCPowerIndex OBJECT-TYPE
			SYNTAX Integer32
			MAX-ACCESS read-only
			STATUS current
			DESCRIPTION
				"直流电源索引。"
			::= { qamModDCPowerEntry 1 }

		
--         1.3.6.1.4.1.1.1.5.11.1.2
-- 1.3.6.1.4.1.17409.1.5.11.1.2
-- 1.3.6.1.4.1.17409.1.5.11.1.2
-- 1.3.6.1.4.1.17409.1.5.11.1.2
-- 1.3.6.1.4.1.17409.1.5.11.1.2
-- 1.3.6.1.4.1.17409.1.5.11.1.2
-- 1.3.6.1.4.1.17409.1.5.11.1.2
-- 1.3.6.1.4.1.17409.1.5.11.1.2
		-- 1.3.6.1.4.1.17409.1.5.11.1.2
		qamModDCPowerVoltage OBJECT-TYPE
			SYNTAX INTEGER (-32768..32767)
			MAX-ACCESS read-only
			STATUS current
			DESCRIPTION
				"电源电压，单位为0.1V。此对象要求在属性MIB中登记一个条目。"
			::= { qamModDCPowerEntry 2 }

		
--         1.3.6.1.4.1.1.1.5.11.1.3
-- 1.3.6.1.4.1.17409.1.5.11.1.3
-- 1.3.6.1.4.1.17409.1.5.11.1.3
-- 1.3.6.1.4.1.17409.1.5.11.1.3
-- 1.3.6.1.4.1.17409.1.5.11.1.3
-- 1.3.6.1.4.1.17409.1.5.11.1.3
-- 1.3.6.1.4.1.17409.1.5.11.1.3
-- 1.3.6.1.4.1.17409.1.5.11.1.3
		-- 1.3.6.1.4.1.17409.1.5.11.1.3
		qamModDCPowerCurrent OBJECT-TYPE
			SYNTAX INTEGER (0..65535)
			MAX-ACCESS read-only
			STATUS optional
			DESCRIPTION
				"电源的电流，单位为0.01A。此对象要求在属性MIB中登记一个条目。"
			::= { qamModDCPowerEntry 3 }

		
--         1.3.6.1.4.1.1.1.5.11.1.4
-- 1.3.6.1.4.1.17409.1.5.11.1.4
-- 1.3.6.1.4.1.17409.1.5.11.1.4
-- 1.3.6.1.4.1.17409.1.5.11.1.4
-- 1.3.6.1.4.1.17409.1.5.11.1.4
-- 1.3.6.1.4.1.17409.1.5.11.1.4
-- 1.3.6.1.4.1.17409.1.5.11.1.4
-- 1.3.6.1.4.1.17409.1.5.11.1.4
		-- 1.3.6.1.4.1.17409.1.5.11.1.4
		qamModDCPowerName OBJECT-TYPE
			SYNTAX DisplayString
			MAX-ACCESS read-only
			STATUS current
			DESCRIPTION
				"标明电源的名称，例如：24V直流电源。
				此字段值由用户规定，至少应标明工作电压并将多个电源相互区分开。
				当这张表里的对象产生告警时，此对象名称应放进hfcAlarmEvent陷阱的alarmText对象里。"
			::= { qamModDCPowerEntry 4 }

		
--              DESCRIPTION
-- "QAM调制器(QAM Modulator)MIB的分支节点标识。"
-- "见附录G。"
-- 1.3.6.1.4.1.1.1.6
-- 1.3.6.1.4.1.17409.1.6
-- 1.3.6.1.4.1.17409.1.6
-- 1.3.6.1.4.1.17409.1.6
-- 1.3.6.1.4.1.17409.1.6
-- 1.3.6.1.4.1.17409.1.6
-- 1.3.6.1.4.1.17409.1.6
-- 1.3.6.1.4.1.17409.1.6
		-- 1.3.6.1.4.1.17409.1.6
		otdIdent OBJECT IDENTIFIER ::= { nscrtvHFCemsTree 6 }

		
--         **********************************************************************************************
-- QAM调制解调器MIB
-- **********************************************************************************************
-- 1.3.6.1.4.1.1.1.6.1
-- 1.3.6.1.4.1.17409.1.6.1
-- 1.3.6.1.4.1.17409.1.6.1
-- 1.3.6.1.4.1.17409.1.6.1
-- 1.3.6.1.4.1.17409.1.6.1
-- 1.3.6.1.4.1.17409.1.6.1
-- 1.3.6.1.4.1.17409.1.6.1
-- 1.3.6.1.4.1.17409.1.6.1
		-- 1.3.6.1.4.1.17409.1.6.1
		otdVendorOID OBJECT-TYPE
			SYNTAX OBJECT IDENTIFIER
			MAX-ACCESS read-only
			STATUS optional
			DESCRIPTION
				"此对象提供厂商对直接调制光发送机MIB的扩充，无扩充时此对象应指向直接调制光发送机节点otdIdent。"
			::= { otdIdent 1 }

		
--         1.3.6.1.4.1.1.1.6.2
-- 1.3.6.1.4.1.17409.1.6.2
-- 1.3.6.1.4.1.17409.1.6.2
-- 1.3.6.1.4.1.17409.1.6.2
-- 1.3.6.1.4.1.17409.1.6.2
-- 1.3.6.1.4.1.17409.1.6.2
-- 1.3.6.1.4.1.17409.1.6.2
-- 1.3.6.1.4.1.17409.1.6.2
		-- 1.3.6.1.4.1.17409.1.6.2
		otdSlotNumber OBJECT-TYPE
			SYNTAX INTEGER (0..32767)
			MAX-ACCESS read-only
			STATUS current
			DESCRIPTION
				"下行光发送机数量或机架插槽数量。"
			::= { otdIdent 2 }

		
--         1.3.6.1.4.1.1.1.6.3
-- 1.3.6.1.4.1.17409.1.6.3
-- 1.3.6.1.4.1.17409.1.6.3
-- 1.3.6.1.4.1.17409.1.6.3
-- 1.3.6.1.4.1.17409.1.6.3
-- 1.3.6.1.4.1.17409.1.6.3
-- 1.3.6.1.4.1.17409.1.6.3
-- 1.3.6.1.4.1.17409.1.6.3
		-- 1.3.6.1.4.1.17409.1.6.3
		otdOptDeviceTable OBJECT-TYPE
			SYNTAX SEQUENCE OF OtdOptDeviceEntry
			MAX-ACCESS not-accessible
			STATUS current
			DESCRIPTION
				"下行光发送机信息表。"
			::= { otdIdent 3 }

		
--         1.3.6.1.4.1.1.1.6.3.1
-- 1.3.6.1.4.1.17409.1.6.3.1
-- 1.3.6.1.4.1.17409.1.6.3.1
-- 1.3.6.1.4.1.17409.1.6.3.1
-- 1.3.6.1.4.1.17409.1.6.3.1
-- 1.3.6.1.4.1.17409.1.6.3.1
-- 1.3.6.1.4.1.17409.1.6.3.1
-- 1.3.6.1.4.1.17409.1.6.3.1
		-- 1.3.6.1.4.1.17409.1.6.3.1
		otdOptDeviceEntry OBJECT-TYPE
			SYNTAX OtdOptDeviceEntry
			MAX-ACCESS not-accessible
			STATUS current
			DESCRIPTION
				"下行光发送机信息表目。"
			INDEX { otdIndex }
			::= { otdOptDeviceTable 1 }

		
		OtdOptDeviceEntry ::=
			SEQUENCE { 
				otdIndex
					INTEGER,
				otdLaserWavelength
					DisplayString,
				otdLaserType
					DisplayString,
				otdDriveLevel
					INTEGER,
				otdInputRFLevel
					INTEGER,
				otdInputRFAttenuationRange
					INTEGER,
				otdInputRFAttenuation
					INTEGER,
				otdLaserTemp
					INTEGER,
				otdLaserCurrent
					INTEGER,
				otdOpicalOutputPower
					INTEGER,
				otdTecCurrent
					INTEGER,
				otdAGCControl
					INTEGER,
				otdConfigurationDriveLevel
					Integer32,
				otdConfigurationRFAttenuation
					Integer32,
				otdConfigurationRFChannels
					Integer32
			 }

--         1.3.6.1.4.1.1.1.6.3.1.1
-- 1.3.6.1.4.1.17409.1.6.3.1.1
-- 1.3.6.1.4.1.17409.1.6.3.1.1
-- 1.3.6.1.4.1.17409.1.6.3.1.1
-- 1.3.6.1.4.1.17409.1.6.3.1.1
-- 1.3.6.1.4.1.17409.1.6.3.1.1
-- 1.3.6.1.4.1.17409.1.6.3.1.1
-- 1.3.6.1.4.1.17409.1.6.3.1.1
		-- 1.3.6.1.4.1.17409.1.6.3.1.1
		otdIndex OBJECT-TYPE
			SYNTAX INTEGER (0..32767)
			MAX-ACCESS read-only
			STATUS current
			DESCRIPTION
				"下行光发送机索引,可以是光发送机编号或机架插槽号。"
			::= { otdOptDeviceEntry 1 }

		
--         1.3.6.1.4.1.1.1.6.3.1.2
-- 1.3.6.1.4.1.17409.1.6.3.1.2
-- 1.3.6.1.4.1.17409.1.6.3.1.2
-- 1.3.6.1.4.1.17409.1.6.3.1.2
-- 1.3.6.1.4.1.17409.1.6.3.1.2
-- 1.3.6.1.4.1.17409.1.6.3.1.2
-- 1.3.6.1.4.1.17409.1.6.3.1.2
-- 1.3.6.1.4.1.17409.1.6.3.1.2
		-- 1.3.6.1.4.1.17409.1.6.3.1.2
		otdLaserWavelength OBJECT-TYPE
			SYNTAX DisplayString
			MAX-ACCESS read-only
			STATUS current
			DESCRIPTION
				"激光器波长。"
			::= { otdOptDeviceEntry 2 }

		
--         1.3.6.1.4.1.1.1.6.3.1.3
-- 1.3.6.1.4.1.17409.1.6.3.1.3
-- 1.3.6.1.4.1.17409.1.6.3.1.3
-- 1.3.6.1.4.1.17409.1.6.3.1.3
-- 1.3.6.1.4.1.17409.1.6.3.1.3
-- 1.3.6.1.4.1.17409.1.6.3.1.3
-- 1.3.6.1.4.1.17409.1.6.3.1.3
-- 1.3.6.1.4.1.17409.1.6.3.1.3
		-- 1.3.6.1.4.1.17409.1.6.3.1.3
		otdLaserType OBJECT-TYPE
			SYNTAX DisplayString
			MAX-ACCESS read-only
			STATUS optional
			DESCRIPTION
				"激光器类型，有效值为unisolated FP, isolated FP, uncooled DFB, cooled DFB,ITU等。"
			::= { otdOptDeviceEntry 3 }

		
--         1.3.6.1.4.1.1.1.6.3.1.4
-- 1.3.6.1.4.1.17409.1.6.3.1.4
-- 1.3.6.1.4.1.17409.1.6.3.1.4
-- 1.3.6.1.4.1.17409.1.6.3.1.4
-- 1.3.6.1.4.1.17409.1.6.3.1.4
-- 1.3.6.1.4.1.17409.1.6.3.1.4
-- 1.3.6.1.4.1.17409.1.6.3.1.4
-- 1.3.6.1.4.1.17409.1.6.3.1.4
		-- 1.3.6.1.4.1.17409.1.6.3.1.4
		otdDriveLevel OBJECT-TYPE
			SYNTAX INTEGER (0..127)
			MAX-ACCESS read-only
			STATUS optional
			DESCRIPTION
				"光模块激励电平,单位为dBuV/ch。此对象要求在属性MIB中登记一个条目。"
			::= { otdOptDeviceEntry 4 }

		
--         1.3.6.1.4.1.1.1.6.3.1.5
-- 1.3.6.1.4.1.17409.1.6.3.1.5
-- 1.3.6.1.4.1.17409.1.6.3.1.5
-- 1.3.6.1.4.1.17409.1.6.3.1.5
-- 1.3.6.1.4.1.17409.1.6.3.1.5
-- 1.3.6.1.4.1.17409.1.6.3.1.5
-- 1.3.6.1.4.1.17409.1.6.3.1.5
-- 1.3.6.1.4.1.17409.1.6.3.1.5
		-- 1.3.6.1.4.1.17409.1.6.3.1.5
		otdInputRFLevel OBJECT-TYPE
			SYNTAX INTEGER (0..127)
			MAX-ACCESS read-only
			STATUS optional
			DESCRIPTION
				"输入射频信号电平,单位为dBuV/ch。此对象要求在属性MIB中登记一个条目。"
			::= { otdOptDeviceEntry 5 }

		
--         1.3.6.1.4.1.1.1.6.3.1.6
-- 1.3.6.1.4.1.17409.1.6.3.1.6
-- 1.3.6.1.4.1.17409.1.6.3.1.6
-- 1.3.6.1.4.1.17409.1.6.3.1.6
-- 1.3.6.1.4.1.17409.1.6.3.1.6
-- 1.3.6.1.4.1.17409.1.6.3.1.6
-- 1.3.6.1.4.1.17409.1.6.3.1.6
-- 1.3.6.1.4.1.17409.1.6.3.1.6
		-- 1.3.6.1.4.1.17409.1.6.3.1.6
		otdInputRFAttenuationRange OBJECT-TYPE
			SYNTAX INTEGER (0..32767)
			MAX-ACCESS read-only
			STATUS optional
			DESCRIPTION
				"输入射频信号衰减量范围,单位为0.1dB。"
			::= { otdOptDeviceEntry 6 }

		
--         1.3.6.1.4.1.1.1.6.3.1.7
-- 1.3.6.1.4.1.17409.1.6.3.1.7
-- 1.3.6.1.4.1.17409.1.6.3.1.7
-- 1.3.6.1.4.1.17409.1.6.3.1.7
-- 1.3.6.1.4.1.17409.1.6.3.1.7
-- 1.3.6.1.4.1.17409.1.6.3.1.7
-- 1.3.6.1.4.1.17409.1.6.3.1.7
-- 1.3.6.1.4.1.17409.1.6.3.1.7
		-- 1.3.6.1.4.1.17409.1.6.3.1.7
		otdInputRFAttenuation OBJECT-TYPE
			SYNTAX INTEGER (-32768..32767)
			MAX-ACCESS read-only
			STATUS optional
			DESCRIPTION
				"输入射频信号衰减量,单位为0.1dB。"
			::= { otdOptDeviceEntry 7 }

		
--         1.3.6.1.4.1.1.1.6.3.1.8
-- 1.3.6.1.4.1.17409.1.6.3.1.8
-- 1.3.6.1.4.1.17409.1.6.3.1.8
-- 1.3.6.1.4.1.17409.1.6.3.1.8
-- 1.3.6.1.4.1.17409.1.6.3.1.8
-- 1.3.6.1.4.1.17409.1.6.3.1.8
-- 1.3.6.1.4.1.17409.1.6.3.1.8
-- 1.3.6.1.4.1.17409.1.6.3.1.8
		-- 1.3.6.1.4.1.17409.1.6.3.1.8
		otdLaserTemp OBJECT-TYPE
			SYNTAX INTEGER (-32768..32767)
			MAX-ACCESS read-only
			STATUS current
			DESCRIPTION
				"激光器工作温度,单位为0.1摄氏度。此对象要求在属性MIB中登记一个条目。"
			::= { otdOptDeviceEntry 8 }

		
--         1.3.6.1.4.1.1.1.6.3.1.9
-- 1.3.6.1.4.1.17409.1.6.3.1.9
-- 1.3.6.1.4.1.17409.1.6.3.1.9
-- 1.3.6.1.4.1.17409.1.6.3.1.9
-- 1.3.6.1.4.1.17409.1.6.3.1.9
-- 1.3.6.1.4.1.17409.1.6.3.1.9
-- 1.3.6.1.4.1.17409.1.6.3.1.9
-- 1.3.6.1.4.1.17409.1.6.3.1.9
		-- 1.3.6.1.4.1.17409.1.6.3.1.9
		otdLaserCurrent OBJECT-TYPE
			SYNTAX INTEGER (-32768..32767)
			MAX-ACCESS read-only
			STATUS current
			DESCRIPTION
				"激光器工作电流,单位为0.1mA。此对象要求在属性MIB中登记一个条目。"
			::= { otdOptDeviceEntry 9 }

		
--         1.3.6.1.4.1.1.1.6.3.1.10
-- 1.3.6.1.4.1.17409.1.6.3.1.10
-- 1.3.6.1.4.1.17409.1.6.3.1.10
-- 1.3.6.1.4.1.17409.1.6.3.1.10
-- 1.3.6.1.4.1.17409.1.6.3.1.10
-- 1.3.6.1.4.1.17409.1.6.3.1.10
-- 1.3.6.1.4.1.17409.1.6.3.1.10
-- 1.3.6.1.4.1.17409.1.6.3.1.10
		-- 1.3.6.1.4.1.17409.1.6.3.1.10
		otdOpicalOutputPower OBJECT-TYPE
			SYNTAX INTEGER (0..32767)
			MAX-ACCESS read-only
			STATUS current
			DESCRIPTION
				"输出光功率,单位为0.1mW。此对象要求在属性MIB中登记一个条目。"
			::= { otdOptDeviceEntry 10 }

		
--         1.3.6.1.4.1.1.1.6.3.1.11
-- 1.3.6.1.4.1.17409.1.6.3.1.11
-- 1.3.6.1.4.1.17409.1.6.3.1.11
-- 1.3.6.1.4.1.17409.1.6.3.1.11
-- 1.3.6.1.4.1.17409.1.6.3.1.11
-- 1.3.6.1.4.1.17409.1.6.3.1.11
-- 1.3.6.1.4.1.17409.1.6.3.1.11
-- 1.3.6.1.4.1.17409.1.6.3.1.11
		-- 1.3.6.1.4.1.17409.1.6.3.1.11
		otdTecCurrent OBJECT-TYPE
			SYNTAX INTEGER (-32768..32767)
			MAX-ACCESS read-only
			STATUS optional
			DESCRIPTION
				"激光器制冷电流,单位为0.01A。此对象要求在属性MIB中登记一个条目。"
			::= { otdOptDeviceEntry 11 }

		
--         1.3.6.1.4.1.1.1.6.3.1.12
-- 1.3.6.1.4.1.17409.1.6.3.1.12
-- 1.3.6.1.4.1.17409.1.6.3.1.12
-- 1.3.6.1.4.1.17409.1.6.3.1.12
-- 1.3.6.1.4.1.17409.1.6.3.1.12
-- 1.3.6.1.4.1.17409.1.6.3.1.12
-- 1.3.6.1.4.1.17409.1.6.3.1.12
-- 1.3.6.1.4.1.17409.1.6.3.1.12
		-- 1.3.6.1.4.1.17409.1.6.3.1.12
		otdAGCControl OBJECT-TYPE
			SYNTAX INTEGER
				{
				off(1),
				on(2)
				}
			MAX-ACCESS read-write
			STATUS optional
			DESCRIPTION
				"AGC控制使能。"
			::= { otdOptDeviceEntry 12 }

		
--         1.3.6.1.4.1.1.1.6.3.1.13
-- 1.3.6.1.4.1.17409.1.6.3.1.13
-- 1.3.6.1.4.1.17409.1.6.3.1.13
-- 1.3.6.1.4.1.17409.1.6.3.1.13
-- 1.3.6.1.4.1.17409.1.6.3.1.13
-- 1.3.6.1.4.1.17409.1.6.3.1.13
-- 1.3.6.1.4.1.17409.1.6.3.1.13
-- 1.3.6.1.4.1.17409.1.6.3.1.13
		-- 1.3.6.1.4.1.17409.1.6.3.1.13
		otdConfigurationDriveLevel OBJECT-TYPE
			SYNTAX Integer32
			MAX-ACCESS read-write
			STATUS optional
			DESCRIPTION
				"设定激光器RF驱动电平偏移量，单位为0.1dB。该参数仅在AGC模式为打开时起作用。系统根据该设定自动调整RF增益（衰减），从而达到设定的激光器RF驱动电平偏移量。"
			::= { otdOptDeviceEntry 13 }

		
--         1.3.6.1.4.1.1.1.6.3.1.14
-- 1.3.6.1.4.1.17409.1.6.3.1.14
-- 1.3.6.1.4.1.17409.1.6.3.1.14
-- 1.3.6.1.4.1.17409.1.6.3.1.14
-- 1.3.6.1.4.1.17409.1.6.3.1.14
-- 1.3.6.1.4.1.17409.1.6.3.1.14
-- 1.3.6.1.4.1.17409.1.6.3.1.14
-- 1.3.6.1.4.1.17409.1.6.3.1.14
		-- 1.3.6.1.4.1.17409.1.6.3.1.14
		otdConfigurationRFAttenuation OBJECT-TYPE
			SYNTAX Integer32
			MAX-ACCESS read-write
			STATUS optional
			DESCRIPTION
				"设定激光器RF驱动信号增益（衰减）的偏移量，单位为0.1dB。该参数仅在AGC模式为关闭时起作用（MGC）。系统根据该设定调整RF信道的增益（衰减），从而达到手动控制激光器RF驱动电平的目的。"
			::= { otdOptDeviceEntry 14 }

		
--         1.3.6.1.4.1.1.1.6.3.1.15
-- 1.3.6.1.4.1.17409.1.6.3.1.15
-- 1.3.6.1.4.1.17409.1.6.3.1.15
-- 1.3.6.1.4.1.17409.1.6.3.1.15
-- 1.3.6.1.4.1.17409.1.6.3.1.15
-- 1.3.6.1.4.1.17409.1.6.3.1.15
-- 1.3.6.1.4.1.17409.1.6.3.1.15
-- 1.3.6.1.4.1.17409.1.6.3.1.15
		-- 1.3.6.1.4.1.17409.1.6.3.1.15
		otdConfigurationRFChannels OBJECT-TYPE
			SYNTAX Integer32
			MAX-ACCESS read-write
			STATUS optional
			DESCRIPTION
				"RF信号中输入的电视信号频道数。"
			::= { otdOptDeviceEntry 15 }

		
--         1.3.6.1.4.1.1.1.6.4
-- 1.3.6.1.4.1.17409.1.6.4
-- 1.3.6.1.4.1.17409.1.6.4
-- 1.3.6.1.4.1.17409.1.6.4
-- 1.3.6.1.4.1.17409.1.6.4
-- 1.3.6.1.4.1.17409.1.6.4
-- 1.3.6.1.4.1.17409.1.6.4
-- 1.3.6.1.4.1.17409.1.6.4
		-- 1.3.6.1.4.1.17409.1.6.4
		otdFansNumber OBJECT-TYPE
			SYNTAX Integer32
			MAX-ACCESS read-only
			STATUS current
			DESCRIPTION
				"表示内部散热风扇的数量，'0'表示设备不支持散热风扇的监测或没有散热风扇。"
			::= { otdIdent 4 }

		
--         1.3.6.1.4.1.1.1.6.5
-- 1.3.6.1.4.1.17409.1.6.5
-- 1.3.6.1.4.1.17409.1.6.5
-- 1.3.6.1.4.1.17409.1.6.5
-- 1.3.6.1.4.1.17409.1.6.5
-- 1.3.6.1.4.1.17409.1.6.5
-- 1.3.6.1.4.1.17409.1.6.5
-- 1.3.6.1.4.1.17409.1.6.5
		-- 1.3.6.1.4.1.17409.1.6.5
		otdFansTable OBJECT-TYPE
			SYNTAX SEQUENCE OF OtdFansEntry
			MAX-ACCESS not-accessible
			STATUS optional
			DESCRIPTION
				"散热风扇信息表。"
			::= { otdIdent 5 }

		
--         1.3.6.1.4.1.1.1.6.5.1
-- 1.3.6.1.4.1.17409.1.6.5.1
-- 1.3.6.1.4.1.17409.1.6.5.1
-- 1.3.6.1.4.1.17409.1.6.5.1
-- 1.3.6.1.4.1.17409.1.6.5.1
-- 1.3.6.1.4.1.17409.1.6.5.1
-- 1.3.6.1.4.1.17409.1.6.5.1
-- 1.3.6.1.4.1.17409.1.6.5.1
		-- 1.3.6.1.4.1.17409.1.6.5.1
		otdFansEntry OBJECT-TYPE
			SYNTAX OtdFansEntry
			MAX-ACCESS not-accessible
			STATUS optional
			DESCRIPTION
				"散热风扇信息表目。"
			INDEX { otdFansIndex }
			::= { otdFansTable 1 }

		
		OtdFansEntry ::=
			SEQUENCE { 
				otdFansIndex
					Integer32,
				otdFansState
					INTEGER,
				otdFansSpeed
					Integer32,
				otdFansControl
					INTEGER,
				otdFansName
					DisplayString
			 }

--         1.3.6.1.4.1.1.1.6.5.1.1
-- 1.3.6.1.4.1.17409.1.6.5.1.1
-- 1.3.6.1.4.1.17409.1.6.5.1.1
-- 1.3.6.1.4.1.17409.1.6.5.1.1
-- 1.3.6.1.4.1.17409.1.6.5.1.1
-- 1.3.6.1.4.1.17409.1.6.5.1.1
-- 1.3.6.1.4.1.17409.1.6.5.1.1
-- 1.3.6.1.4.1.17409.1.6.5.1.1
		-- 1.3.6.1.4.1.17409.1.6.5.1.1
		otdFansIndex OBJECT-TYPE
			SYNTAX Integer32
			MAX-ACCESS read-only
			STATUS optional
			DESCRIPTION
				"散热风扇信息表索引。"
			::= { otdFansEntry 1 }

		
--         1.3.6.1.4.1.1.1.6.5.1.2
-- 1.3.6.1.4.1.17409.1.6.5.1.2
-- 1.3.6.1.4.1.17409.1.6.5.1.2
-- 1.3.6.1.4.1.17409.1.6.5.1.2
-- 1.3.6.1.4.1.17409.1.6.5.1.2
-- 1.3.6.1.4.1.17409.1.6.5.1.2
-- 1.3.6.1.4.1.17409.1.6.5.1.2
-- 1.3.6.1.4.1.17409.1.6.5.1.2
		-- 1.3.6.1.4.1.17409.1.6.5.1.2
		otdFansState OBJECT-TYPE
			SYNTAX INTEGER
				{
				normal(1),
				fault(2),
				off(3)
				}
			MAX-ACCESS read-only
			STATUS optional
			DESCRIPTION
				"散热风扇工作状态，normal 表示正常, fault表示失效,off表示关闭。此对象要求在属性MIB中登记一个条目。"
			::= { otdFansEntry 2 }

		
--         1.3.6.1.4.1.1.1.6.5.1.3
-- 1.3.6.1.4.1.17409.1.6.5.1.3
-- 1.3.6.1.4.1.17409.1.6.5.1.3
-- 1.3.6.1.4.1.17409.1.6.5.1.3
-- 1.3.6.1.4.1.17409.1.6.5.1.3
-- 1.3.6.1.4.1.17409.1.6.5.1.3
-- 1.3.6.1.4.1.17409.1.6.5.1.3
-- 1.3.6.1.4.1.17409.1.6.5.1.3
		-- 1.3.6.1.4.1.17409.1.6.5.1.3
		otdFansSpeed OBJECT-TYPE
			SYNTAX Integer32
			MAX-ACCESS read-only
			STATUS optional
			DESCRIPTION
				"散热风扇工作时的转速，单位为转/分，不支持转速检测时可置为'0'。此对象要求在属性MIB中登记一个条目。"
			::= { otdFansEntry 3 }

		
--         1.3.6.1.4.1.1.1.6.5.1.4
-- 1.3.6.1.4.1.17409.1.6.5.1.4
-- 1.3.6.1.4.1.17409.1.6.5.1.4
-- 1.3.6.1.4.1.17409.1.6.5.1.4
-- 1.3.6.1.4.1.17409.1.6.5.1.4
-- 1.3.6.1.4.1.17409.1.6.5.1.4
-- 1.3.6.1.4.1.17409.1.6.5.1.4
-- 1.3.6.1.4.1.17409.1.6.5.1.4
		-- 1.3.6.1.4.1.17409.1.6.5.1.4
		otdFansControl OBJECT-TYPE
			SYNTAX INTEGER
				{
				on(1),
				off(2)
				}
			MAX-ACCESS read-write
			STATUS optional
			DESCRIPTION
				"散热风扇工作控制。 "
			::= { otdFansEntry 4 }

		
--         1.3.6.1.4.1.1.1.6.5.1.5
-- 1.3.6.1.4.1.17409.1.6.5.1.5
-- 1.3.6.1.4.1.17409.1.6.5.1.5
-- 1.3.6.1.4.1.17409.1.6.5.1.5
-- 1.3.6.1.4.1.17409.1.6.5.1.5
-- 1.3.6.1.4.1.17409.1.6.5.1.5
-- 1.3.6.1.4.1.17409.1.6.5.1.5
-- 1.3.6.1.4.1.17409.1.6.5.1.5
		-- 1.3.6.1.4.1.17409.1.6.5.1.5
		otdFansName OBJECT-TYPE
			SYNTAX DisplayString
			MAX-ACCESS read-only
			STATUS optional
			DESCRIPTION
				"散热风扇名称。"
			::= { otdFansEntry 5 }

		
--         1.3.6.1.4.1.1.1.6.6
-- 1.3.6.1.4.1.17409.1.6.6
-- 1.3.6.1.4.1.17409.1.6.6
-- 1.3.6.1.4.1.17409.1.6.6
-- 1.3.6.1.4.1.17409.1.6.6
-- 1.3.6.1.4.1.17409.1.6.6
-- 1.3.6.1.4.1.17409.1.6.6
-- 1.3.6.1.4.1.17409.1.6.6
		-- 1.3.6.1.4.1.17409.1.6.6
		otdNumberDCPowerSupply OBJECT-TYPE
			SYNTAX INTEGER (0..16)
			MAX-ACCESS read-only
			STATUS current
			DESCRIPTION
				"直流电源数量，'0'表示应答器不支持此功能。"
			::= { otdIdent 6 }

		
--         1.3.6.1.4.1.1.1.6.7
-- 1.3.6.1.4.1.17409.1.6.7
-- 1.3.6.1.4.1.17409.1.6.7
-- 1.3.6.1.4.1.17409.1.6.7
-- 1.3.6.1.4.1.17409.1.6.7
-- 1.3.6.1.4.1.17409.1.6.7
-- 1.3.6.1.4.1.17409.1.6.7
-- 1.3.6.1.4.1.17409.1.6.7
		-- 1.3.6.1.4.1.17409.1.6.7
		otdDCPowerSupplyMode OBJECT-TYPE
			SYNTAX INTEGER
				{
				loadsharing(1),
				switchedredundant(2),
				alonesupply(3)
				}
			MAX-ACCESS read-only
			STATUS optional
			DESCRIPTION
				"供电电源工作模式。"
			::= { otdIdent 7 }

		
--         1.3.6.1.4.1.1.1.6.8
-- 1.3.6.1.4.1.17409.1.6.8
-- 1.3.6.1.4.1.17409.1.6.8
-- 1.3.6.1.4.1.17409.1.6.8
-- 1.3.6.1.4.1.17409.1.6.8
-- 1.3.6.1.4.1.17409.1.6.8
-- 1.3.6.1.4.1.17409.1.6.8
-- 1.3.6.1.4.1.17409.1.6.8
		-- 1.3.6.1.4.1.17409.1.6.8
		otdDCPowerTable OBJECT-TYPE
			SYNTAX SEQUENCE OF OtdDCPowerEntry
			MAX-ACCESS not-accessible
			STATUS current
			DESCRIPTION
				"直流电源信息表。"
			::= { otdIdent 8 }

		
--         1.3.6.1.4.1.1.1.6.8.1
-- 1.3.6.1.4.1.17409.1.6.8.1
-- 1.3.6.1.4.1.17409.1.6.8.1
-- 1.3.6.1.4.1.17409.1.6.8.1
-- 1.3.6.1.4.1.17409.1.6.8.1
-- 1.3.6.1.4.1.17409.1.6.8.1
-- 1.3.6.1.4.1.17409.1.6.8.1
-- 1.3.6.1.4.1.17409.1.6.8.1
		-- 1.3.6.1.4.1.17409.1.6.8.1
		otdDCPowerEntry OBJECT-TYPE
			SYNTAX OtdDCPowerEntry
			MAX-ACCESS not-accessible
			STATUS current
			DESCRIPTION
				"直流电源信息表目。"
			INDEX { otdDCPowerIndex }
			::= { otdDCPowerTable 1 }

		
		OtdDCPowerEntry ::=
			SEQUENCE { 
				otdDCPowerIndex
					Integer32,
				otdDCPowerVoltage
					INTEGER,
				otdDCPowerCurrent
					INTEGER,
				otdDCPowerName
					DisplayString
			 }

--         1.3.6.1.4.1.1.1.6.8.1.1
-- 1.3.6.1.4.1.17409.1.6.8.1.1
-- 1.3.6.1.4.1.17409.1.6.8.1.1
-- 1.3.6.1.4.1.17409.1.6.8.1.1
-- 1.3.6.1.4.1.17409.1.6.8.1.1
-- 1.3.6.1.4.1.17409.1.6.8.1.1
-- 1.3.6.1.4.1.17409.1.6.8.1.1
-- 1.3.6.1.4.1.17409.1.6.8.1.1
		-- 1.3.6.1.4.1.17409.1.6.8.1.1
		otdDCPowerIndex OBJECT-TYPE
			SYNTAX Integer32
			MAX-ACCESS read-only
			STATUS current
			DESCRIPTION
				"直流电源索引。"
			::= { otdDCPowerEntry 1 }

		
--         1.3.6.1.4.1.1.1.6.8.1.2
-- 1.3.6.1.4.1.17409.1.6.8.1.2
-- 1.3.6.1.4.1.17409.1.6.8.1.2
-- 1.3.6.1.4.1.17409.1.6.8.1.2
-- 1.3.6.1.4.1.17409.1.6.8.1.2
-- 1.3.6.1.4.1.17409.1.6.8.1.2
-- 1.3.6.1.4.1.17409.1.6.8.1.2
-- 1.3.6.1.4.1.17409.1.6.8.1.2
		-- 1.3.6.1.4.1.17409.1.6.8.1.2
		otdDCPowerVoltage OBJECT-TYPE
			SYNTAX INTEGER (-32768..32767)
			MAX-ACCESS read-only
			STATUS current
			DESCRIPTION
				"电源电压，单位为0.1V。此对象要求在属性MIB中登记一个条目。"
			::= { otdDCPowerEntry 2 }

		
--         1.3.6.1.4.1.1.1.6.8.1.3
-- 1.3.6.1.4.1.17409.1.6.8.1.3
-- 1.3.6.1.4.1.17409.1.6.8.1.3
-- 1.3.6.1.4.1.17409.1.6.8.1.3
-- 1.3.6.1.4.1.17409.1.6.8.1.3
-- 1.3.6.1.4.1.17409.1.6.8.1.3
-- 1.3.6.1.4.1.17409.1.6.8.1.3
-- 1.3.6.1.4.1.17409.1.6.8.1.3
		-- 1.3.6.1.4.1.17409.1.6.8.1.3
		otdDCPowerCurrent OBJECT-TYPE
			SYNTAX INTEGER (0..65535)
			MAX-ACCESS read-only
			STATUS optional
			DESCRIPTION
				"电源电流，单位为0.1A。此对象要求在属性MIB中登记一个条目。"
			::= { otdDCPowerEntry 3 }

		
--         1.3.6.1.4.1.1.1.6.8.1.4
-- 1.3.6.1.4.1.17409.1.6.8.1.4
-- 1.3.6.1.4.1.17409.1.6.8.1.4
-- 1.3.6.1.4.1.17409.1.6.8.1.4
-- 1.3.6.1.4.1.17409.1.6.8.1.4
-- 1.3.6.1.4.1.17409.1.6.8.1.4
-- 1.3.6.1.4.1.17409.1.6.8.1.4
-- 1.3.6.1.4.1.17409.1.6.8.1.4
		-- 1.3.6.1.4.1.17409.1.6.8.1.4
		otdDCPowerName OBJECT-TYPE
			SYNTAX DisplayString
			MAX-ACCESS read-only
			STATUS current
			DESCRIPTION
				"标明电源的名称，例如：24V直流电源。
				此字段值由用户规定，至少应标明工作电压并将多个电源相互区分开。
				当表中的对象产生告警时，此对象名称应放进hfcAlarmEvent陷阱的alarmText对象里（见附录D）。"
			::= { otdDCPowerEntry 4 }

		
--              DESCRIPTION
-- "直接调制光发送机MIB的分支节点标识。"
-- "见附录H。"
-- 1.3.6.1.4.1.1.1.7
-- 1.3.6.1.4.1.17409.1.7
-- 1.3.6.1.4.1.17409.1.7
-- 1.3.6.1.4.1.17409.1.7
-- 1.3.6.1.4.1.17409.1.7
-- 1.3.6.1.4.1.17409.1.7
-- 1.3.6.1.4.1.17409.1.7
-- 1.3.6.1.4.1.17409.1.7
		-- 1.3.6.1.4.1.17409.1.7
		otxIdent OBJECT IDENTIFIER ::= { nscrtvHFCemsTree 7 }

		
--         **********************************************************************************************
-- 外调制光发送机MIB
-- **********************************************************************************************
-- 1.3.6.1.4.1.1.1.7.1
-- 1.3.6.1.4.1.17409.1.7.1
-- 1.3.6.1.4.1.17409.1.7.1
-- 1.3.6.1.4.1.17409.1.7.1
-- 1.3.6.1.4.1.17409.1.7.1
-- 1.3.6.1.4.1.17409.1.7.1
-- 1.3.6.1.4.1.17409.1.7.1
-- 1.3.6.1.4.1.17409.1.7.1
		-- 1.3.6.1.4.1.17409.1.7.1
		otxVendorOID OBJECT-TYPE
			SYNTAX OBJECT IDENTIFIER
			MAX-ACCESS read-only
			STATUS optional
			DESCRIPTION
				"此对象提供厂商对外调制光发送机MIB的扩充,无扩充时此对象应指向外调制光发送机节点otxIdent。"
			::= { otxIdent 1 }

		
--         1.3.6.1.4.1.1.1.7.2
-- 1.3.6.1.4.1.17409.1.7.2
-- 1.3.6.1.4.1.17409.1.7.2
-- 1.3.6.1.4.1.17409.1.7.2
-- 1.3.6.1.4.1.17409.1.7.2
-- 1.3.6.1.4.1.17409.1.7.2
-- 1.3.6.1.4.1.17409.1.7.2
-- 1.3.6.1.4.1.17409.1.7.2
		-- 1.3.6.1.4.1.17409.1.7.2
		otxSlotNumber OBJECT-TYPE
			SYNTAX Integer32
			MAX-ACCESS read-only
			STATUS current
			DESCRIPTION
				"外调制光发送机中发送模块的数量。"
			::= { otxIdent 2 }

		
--         1.3.6.1.4.1.1.1.7.3
-- 1.3.6.1.4.1.17409.1.7.3
-- 1.3.6.1.4.1.17409.1.7.3
-- 1.3.6.1.4.1.17409.1.7.3
-- 1.3.6.1.4.1.17409.1.7.3
-- 1.3.6.1.4.1.17409.1.7.3
-- 1.3.6.1.4.1.17409.1.7.3
-- 1.3.6.1.4.1.17409.1.7.3
		-- 1.3.6.1.4.1.17409.1.7.3
		otxModuleTable OBJECT-TYPE
			SYNTAX SEQUENCE OF OtxModuleEntry
			MAX-ACCESS not-accessible
			STATUS current
			DESCRIPTION
				"外调制光发送机发送模块表。"
			::= { otxIdent 3 }

		
--         1.3.6.1.4.1.1.1.7.3.1
-- 1.3.6.1.4.1.17409.1.7.3.1
-- 1.3.6.1.4.1.17409.1.7.3.1
-- 1.3.6.1.4.1.17409.1.7.3.1
-- 1.3.6.1.4.1.17409.1.7.3.1
-- 1.3.6.1.4.1.17409.1.7.3.1
-- 1.3.6.1.4.1.17409.1.7.3.1
-- 1.3.6.1.4.1.17409.1.7.3.1
		-- 1.3.6.1.4.1.17409.1.7.3.1
		otxModuleEntry OBJECT-TYPE
			SYNTAX OtxModuleEntry
			MAX-ACCESS not-accessible
			STATUS current
			DESCRIPTION
				"外调制光发送机发送模块表目。"
			INDEX { otxModuleIndex }
			::= { otxModuleTable 1 }

		
		OtxModuleEntry ::=
			SEQUENCE { 
				otxModuleIndex
					Integer32,
				otxLaserControl
					INTEGER,
				otxConfigurationAGCMode
					INTEGER,
				otxConfigurationOmi
					Integer32,
				otxConfigurationRfGain
					Integer32,
				otxConfigurationSbsSuppression
					Integer32,
				otxConfigurationChannelDistance
					Integer32,
				otxConfigurationItuFrequency
					Integer32,
				otxItuFrequencyMin
					Integer32,
				otxItuFrequencyMax
					Integer32,
				otxItuFrequencyStep
					Integer32,
				otxInputRFLevel
					Integer32,
				otxRfGain
					Integer32,
				otxLaserCurrent
					Integer32,
				otxLaserOutputPower
					Integer32,
				otxLaserTemperature
					Integer32,
				otxLaserTecCurrent
					Integer32,
				otxOmi
					Integer32
			 }

--         1.3.6.1.4.1.1.1.7.3.1.1
-- 1.3.6.1.4.1.17409.1.7.3.1.1
-- 1.3.6.1.4.1.17409.1.7.3.1.1
-- 1.3.6.1.4.1.17409.1.7.3.1.1
-- 1.3.6.1.4.1.17409.1.7.3.1.1
-- 1.3.6.1.4.1.17409.1.7.3.1.1
-- 1.3.6.1.4.1.17409.1.7.3.1.1
-- 1.3.6.1.4.1.17409.1.7.3.1.1
		-- 1.3.6.1.4.1.17409.1.7.3.1.1
		otxModuleIndex OBJECT-TYPE
			SYNTAX Integer32
			MAX-ACCESS read-only
			STATUS current
			DESCRIPTION
				"外调制光发送机发送模块表索引。"
			::= { otxModuleEntry 1 }

		
--         1.3.6.1.4.1.1.1.7.3.1.2
-- 1.3.6.1.4.1.17409.1.7.3.1.2
-- 1.3.6.1.4.1.17409.1.7.3.1.2
-- 1.3.6.1.4.1.17409.1.7.3.1.2
-- 1.3.6.1.4.1.17409.1.7.3.1.2
-- 1.3.6.1.4.1.17409.1.7.3.1.2
-- 1.3.6.1.4.1.17409.1.7.3.1.2
-- 1.3.6.1.4.1.17409.1.7.3.1.2
		-- 1.3.6.1.4.1.17409.1.7.3.1.2
		otxLaserControl OBJECT-TYPE
			SYNTAX INTEGER
				{
				on(1),
				off(2)
				}
			MAX-ACCESS read-write
			STATUS current
			DESCRIPTION
				"外调制光发送机发送模块控制。"
			::= { otxModuleEntry 2 }

		
--         1.3.6.1.4.1.1.1.7.3.1.3
-- 1.3.6.1.4.1.17409.1.7.3.1.3
-- 1.3.6.1.4.1.17409.1.7.3.1.3
-- 1.3.6.1.4.1.17409.1.7.3.1.3
-- 1.3.6.1.4.1.17409.1.7.3.1.3
-- 1.3.6.1.4.1.17409.1.7.3.1.3
-- 1.3.6.1.4.1.17409.1.7.3.1.3
-- 1.3.6.1.4.1.17409.1.7.3.1.3
		-- 1.3.6.1.4.1.17409.1.7.3.1.3
		otxConfigurationAGCMode OBJECT-TYPE
			SYNTAX INTEGER
				{
				modeAgcOff(1),
				modeCWUnmodulatedAgcOn(2),
				modeVideoModulatedAgcOn(3)
				}
			MAX-ACCESS read-write
			STATUS optional
			DESCRIPTION
				"外调制光发送机的AGC模式控制。"
			::= { otxModuleEntry 3 }

		
--         1.3.6.1.4.1.1.1.7.3.1.4
-- 1.3.6.1.4.1.17409.1.7.3.1.4
-- 1.3.6.1.4.1.17409.1.7.3.1.4
-- 1.3.6.1.4.1.17409.1.7.3.1.4
-- 1.3.6.1.4.1.17409.1.7.3.1.4
-- 1.3.6.1.4.1.17409.1.7.3.1.4
-- 1.3.6.1.4.1.17409.1.7.3.1.4
-- 1.3.6.1.4.1.17409.1.7.3.1.4
		-- 1.3.6.1.4.1.17409.1.7.3.1.4
		otxConfigurationOmi OBJECT-TYPE
			SYNTAX Integer32
			MAX-ACCESS read-write
			STATUS optional
			DESCRIPTION
				"设定光调制度OMI的偏移量，单位为0.1dB。该参数仅在AGC模式为打开时起作用。系统根据该设定自动调整RF增益，从而达到设定的光调制度偏移量。"
			::= { otxModuleEntry 4 }

		
--         1.3.6.1.4.1.1.1.7.3.1.5
-- 1.3.6.1.4.1.17409.1.7.3.1.5
-- 1.3.6.1.4.1.17409.1.7.3.1.5
-- 1.3.6.1.4.1.17409.1.7.3.1.5
-- 1.3.6.1.4.1.17409.1.7.3.1.5
-- 1.3.6.1.4.1.17409.1.7.3.1.5
-- 1.3.6.1.4.1.17409.1.7.3.1.5
-- 1.3.6.1.4.1.17409.1.7.3.1.5
		-- 1.3.6.1.4.1.17409.1.7.3.1.5
		otxConfigurationRfGain OBJECT-TYPE
			SYNTAX Integer32
			MAX-ACCESS read-write
			STATUS optional
			DESCRIPTION
				"设定RF驱动电平增益的偏移量，单位为0.1dB。该参数仅在AGC模式为关闭时起作用。"
			::= { otxModuleEntry 5 }

		
--         1.3.6.1.4.1.1.1.7.3.1.6
-- 1.3.6.1.4.1.17409.1.7.3.1.6
-- 1.3.6.1.4.1.17409.1.7.3.1.6
-- 1.3.6.1.4.1.17409.1.7.3.1.6
-- 1.3.6.1.4.1.17409.1.7.3.1.6
-- 1.3.6.1.4.1.17409.1.7.3.1.6
-- 1.3.6.1.4.1.17409.1.7.3.1.6
-- 1.3.6.1.4.1.17409.1.7.3.1.6
		-- 1.3.6.1.4.1.17409.1.7.3.1.6
		otxConfigurationSbsSuppression OBJECT-TYPE
			SYNTAX Integer32
			MAX-ACCESS read-write
			STATUS optional
			DESCRIPTION
				"设定SBS阈值，单位为0.1dBm"
			::= { otxModuleEntry 6 }

		
--         1.3.6.1.4.1.1.1.7.3.1.7
-- 1.3.6.1.4.1.17409.1.7.3.1.7
-- 1.3.6.1.4.1.17409.1.7.3.1.7
-- 1.3.6.1.4.1.17409.1.7.3.1.7
-- 1.3.6.1.4.1.17409.1.7.3.1.7
-- 1.3.6.1.4.1.17409.1.7.3.1.7
-- 1.3.6.1.4.1.17409.1.7.3.1.7
-- 1.3.6.1.4.1.17409.1.7.3.1.7
		-- 1.3.6.1.4.1.17409.1.7.3.1.7
		otxConfigurationChannelDistance OBJECT-TYPE
			SYNTAX Integer32
			MAX-ACCESS read-write
			STATUS optional
			DESCRIPTION
				"设定激光器光波的频道值，单位为GHz。 "
			::= { otxModuleEntry 7 }

		
--         1.3.6.1.4.1.1.1.7.3.1.8
-- 1.3.6.1.4.1.17409.1.7.3.1.8
-- 1.3.6.1.4.1.17409.1.7.3.1.8
-- 1.3.6.1.4.1.17409.1.7.3.1.8
-- 1.3.6.1.4.1.17409.1.7.3.1.8
-- 1.3.6.1.4.1.17409.1.7.3.1.8
-- 1.3.6.1.4.1.17409.1.7.3.1.8
-- 1.3.6.1.4.1.17409.1.7.3.1.8
		-- 1.3.6.1.4.1.17409.1.7.3.1.8
		otxConfigurationItuFrequency OBJECT-TYPE
			SYNTAX Integer32
			MAX-ACCESS read-write
			STATUS optional
			DESCRIPTION
				"按照ITU标准设定的激光器光波频率，单位为GHz。 "
			::= { otxModuleEntry 8 }

		
--         1.3.6.1.4.1.1.1.7.3.1.9
-- 1.3.6.1.4.1.17409.1.7.3.1.9
-- 1.3.6.1.4.1.17409.1.7.3.1.9
-- 1.3.6.1.4.1.17409.1.7.3.1.9
-- 1.3.6.1.4.1.17409.1.7.3.1.9
-- 1.3.6.1.4.1.17409.1.7.3.1.9
-- 1.3.6.1.4.1.17409.1.7.3.1.9
-- 1.3.6.1.4.1.17409.1.7.3.1.9
		-- 1.3.6.1.4.1.17409.1.7.3.1.9
		otxItuFrequencyMin OBJECT-TYPE
			SYNTAX Integer32
			MAX-ACCESS read-only
			STATUS optional
			DESCRIPTION
				"按照ITU标准设定的激光器最小光波频率，单位为GHz。 "
			::= { otxModuleEntry 9 }

		
--         1.3.6.1.4.1.1.1.7.3.1.10
-- 1.3.6.1.4.1.17409.1.7.3.1.10
-- 1.3.6.1.4.1.17409.1.7.3.1.10
-- 1.3.6.1.4.1.17409.1.7.3.1.10
-- 1.3.6.1.4.1.17409.1.7.3.1.10
-- 1.3.6.1.4.1.17409.1.7.3.1.10
-- 1.3.6.1.4.1.17409.1.7.3.1.10
-- 1.3.6.1.4.1.17409.1.7.3.1.10
		-- 1.3.6.1.4.1.17409.1.7.3.1.10
		otxItuFrequencyMax OBJECT-TYPE
			SYNTAX Integer32
			MAX-ACCESS read-only
			STATUS optional
			DESCRIPTION
				"按照ITU标准设定的激光器最大光波频率，单位为GHz。 "
			::= { otxModuleEntry 10 }

		
--         1.3.6.1.4.1.1.1.7.3.1.11
-- 1.3.6.1.4.1.17409.1.7.3.1.11
-- 1.3.6.1.4.1.17409.1.7.3.1.11
-- 1.3.6.1.4.1.17409.1.7.3.1.11
-- 1.3.6.1.4.1.17409.1.7.3.1.11
-- 1.3.6.1.4.1.17409.1.7.3.1.11
-- 1.3.6.1.4.1.17409.1.7.3.1.11
-- 1.3.6.1.4.1.17409.1.7.3.1.11
		-- 1.3.6.1.4.1.17409.1.7.3.1.11
		otxItuFrequencyStep OBJECT-TYPE
			SYNTAX Integer32
			MAX-ACCESS read-only
			STATUS optional
			DESCRIPTION
				"按照ITU标准设定的光波频率步长间隔，单位为GHz。 "
			::= { otxModuleEntry 11 }

		
--         1.3.6.1.4.1.1.1.7.3.1.12
-- 1.3.6.1.4.1.17409.1.7.3.1.12
-- 1.3.6.1.4.1.17409.1.7.3.1.12
-- 1.3.6.1.4.1.17409.1.7.3.1.12
-- 1.3.6.1.4.1.17409.1.7.3.1.12
-- 1.3.6.1.4.1.17409.1.7.3.1.12
-- 1.3.6.1.4.1.17409.1.7.3.1.12
-- 1.3.6.1.4.1.17409.1.7.3.1.12
		-- 1.3.6.1.4.1.17409.1.7.3.1.12
		otxInputRFLevel OBJECT-TYPE
			SYNTAX Integer32
			MAX-ACCESS read-only
			STATUS optional
			DESCRIPTION
				"输入RF电平，单位为0.1dBuV。此对象要求在属性MIB中登记一个条目。"
			::= { otxModuleEntry 12 }

		
--         1.3.6.1.4.1.1.1.7.3.1.13
-- 1.3.6.1.4.1.17409.1.7.3.1.13
-- 1.3.6.1.4.1.17409.1.7.3.1.13
-- 1.3.6.1.4.1.17409.1.7.3.1.13
-- 1.3.6.1.4.1.17409.1.7.3.1.13
-- 1.3.6.1.4.1.17409.1.7.3.1.13
-- 1.3.6.1.4.1.17409.1.7.3.1.13
-- 1.3.6.1.4.1.17409.1.7.3.1.13
		-- 1.3.6.1.4.1.17409.1.7.3.1.13
		otxRfGain OBJECT-TYPE
			SYNTAX Integer32
			MAX-ACCESS read-only
			STATUS optional
			DESCRIPTION
				"RF增益的偏移量，单位为0.1dB。当AGC模式关闭时该值等于设定的RF增益偏移量，当AGC模式打开时该值等于达到设定光调制度偏移量时所需的RF增益的偏移量。"
			::= { otxModuleEntry 13 }

		
--         1.3.6.1.4.1.1.1.7.3.1.14
-- 1.3.6.1.4.1.17409.1.7.3.1.14
-- 1.3.6.1.4.1.17409.1.7.3.1.14
-- 1.3.6.1.4.1.17409.1.7.3.1.14
-- 1.3.6.1.4.1.17409.1.7.3.1.14
-- 1.3.6.1.4.1.17409.1.7.3.1.14
-- 1.3.6.1.4.1.17409.1.7.3.1.14
-- 1.3.6.1.4.1.17409.1.7.3.1.14
		-- 1.3.6.1.4.1.17409.1.7.3.1.14
		otxLaserCurrent OBJECT-TYPE
			SYNTAX Integer32
			MAX-ACCESS read-only
			STATUS current
			DESCRIPTION
				"激光器工作电流,单位为mA。此对象要求在属性MIB中登记一个条目。"
			::= { otxModuleEntry 14 }

		
--         1.3.6.1.4.1.1.1.7.3.1.15
-- 1.3.6.1.4.1.17409.1.7.3.1.15
-- 1.3.6.1.4.1.17409.1.7.3.1.15
-- 1.3.6.1.4.1.17409.1.7.3.1.15
-- 1.3.6.1.4.1.17409.1.7.3.1.15
-- 1.3.6.1.4.1.17409.1.7.3.1.15
-- 1.3.6.1.4.1.17409.1.7.3.1.15
-- 1.3.6.1.4.1.17409.1.7.3.1.15
		-- 1.3.6.1.4.1.17409.1.7.3.1.15
		otxLaserOutputPower OBJECT-TYPE
			SYNTAX Integer32
			MAX-ACCESS read-only
			STATUS current
			DESCRIPTION
				"输出光功率,单位为mW。此对象要求在属性MIB中登记一个条目。"
			::= { otxModuleEntry 15 }

		
--         1.3.6.1.4.1.1.1.7.3.1.16
-- 1.3.6.1.4.1.17409.1.7.3.1.16
-- 1.3.6.1.4.1.17409.1.7.3.1.16
-- 1.3.6.1.4.1.17409.1.7.3.1.16
-- 1.3.6.1.4.1.17409.1.7.3.1.16
-- 1.3.6.1.4.1.17409.1.7.3.1.16
-- 1.3.6.1.4.1.17409.1.7.3.1.16
-- 1.3.6.1.4.1.17409.1.7.3.1.16
		-- 1.3.6.1.4.1.17409.1.7.3.1.16
		otxLaserTemperature OBJECT-TYPE
			SYNTAX Integer32
			MAX-ACCESS read-only
			STATUS current
			DESCRIPTION
				"激光器工作温度,单位为0C。此对象要求在属性MIB中登记一个条目。"
			::= { otxModuleEntry 16 }

		
--         1.3.6.1.4.1.1.1.7.3.1.17
-- 1.3.6.1.4.1.17409.1.7.3.1.17
-- 1.3.6.1.4.1.17409.1.7.3.1.17
-- 1.3.6.1.4.1.17409.1.7.3.1.17
-- 1.3.6.1.4.1.17409.1.7.3.1.17
-- 1.3.6.1.4.1.17409.1.7.3.1.17
-- 1.3.6.1.4.1.17409.1.7.3.1.17
-- 1.3.6.1.4.1.17409.1.7.3.1.17
		-- 1.3.6.1.4.1.17409.1.7.3.1.17
		otxLaserTecCurrent OBJECT-TYPE
			SYNTAX Integer32
			MAX-ACCESS read-only
			STATUS current
			DESCRIPTION
				"激光器制冷电流,单位为mA。此对象要求在属性MIB中登记一个条目。"
			::= { otxModuleEntry 17 }

		
--         1.3.6.1.4.1.1.1.7.3.1.18
-- 1.3.6.1.4.1.17409.1.7.3.1.18
-- 1.3.6.1.4.1.17409.1.7.3.1.18
-- 1.3.6.1.4.1.17409.1.7.3.1.18
-- 1.3.6.1.4.1.17409.1.7.3.1.18
-- 1.3.6.1.4.1.17409.1.7.3.1.18
-- 1.3.6.1.4.1.17409.1.7.3.1.18
-- 1.3.6.1.4.1.17409.1.7.3.1.18
		-- 1.3.6.1.4.1.17409.1.7.3.1.18
		otxOmi OBJECT-TYPE
			SYNTAX Integer32
			MAX-ACCESS read-only
			STATUS optional
			DESCRIPTION
				"设备的光调制度偏移量，单位为0.1dB。当AGC模式为打开时，该值等于设定的光调制度偏移量。当AGC模式处于关闭时，该值等于根据设定的RF增益偏移量调整增益后得到的光调制度偏移量。"
			::= { otxModuleEntry 18 }

		
--         1.3.6.1.4.1.1.1.7.4
-- 1.3.6.1.4.1.17409.1.7.4
-- 1.3.6.1.4.1.17409.1.7.4
-- 1.3.6.1.4.1.17409.1.7.4
-- 1.3.6.1.4.1.17409.1.7.4
-- 1.3.6.1.4.1.17409.1.7.4
-- 1.3.6.1.4.1.17409.1.7.4
-- 1.3.6.1.4.1.17409.1.7.4
		-- 1.3.6.1.4.1.17409.1.7.4
		otxFansNumber OBJECT-TYPE
			SYNTAX Integer32
			MAX-ACCESS read-only
			STATUS current
			DESCRIPTION
				"表示内部散热风扇的数量，'0'表示设备不支持散热风扇的监测或没有散热风扇。"
			::= { otxIdent 4 }

		
--         1.3.6.1.4.1.1.1.7.5
-- 1.3.6.1.4.1.17409.1.7.5
-- 1.3.6.1.4.1.17409.1.7.5
-- 1.3.6.1.4.1.17409.1.7.5
-- 1.3.6.1.4.1.17409.1.7.5
-- 1.3.6.1.4.1.17409.1.7.5
-- 1.3.6.1.4.1.17409.1.7.5
-- 1.3.6.1.4.1.17409.1.7.5
		-- 1.3.6.1.4.1.17409.1.7.5
		otxFansTable OBJECT-TYPE
			SYNTAX SEQUENCE OF OtxFansEntry
			MAX-ACCESS not-accessible
			STATUS optional
			DESCRIPTION
				"散热风扇信息表。"
			::= { otxIdent 5 }

		
--         1.3.6.1.4.1.1.1.7.5.1
-- 1.3.6.1.4.1.17409.1.7.5.1
-- 1.3.6.1.4.1.17409.1.7.5.1
-- 1.3.6.1.4.1.17409.1.7.5.1
-- 1.3.6.1.4.1.17409.1.7.5.1
-- 1.3.6.1.4.1.17409.1.7.5.1
-- 1.3.6.1.4.1.17409.1.7.5.1
-- 1.3.6.1.4.1.17409.1.7.5.1
		-- 1.3.6.1.4.1.17409.1.7.5.1
		otxFansEntry OBJECT-TYPE
			SYNTAX OtxFansEntry
			MAX-ACCESS not-accessible
			STATUS optional
			DESCRIPTION
				"散热风扇信息表目。"
			INDEX { otxFansIndex }
			::= { otxFansTable 1 }

		
		OtxFansEntry ::=
			SEQUENCE { 
				otxFansIndex
					Integer32,
				otxFansState
					INTEGER,
				otxFansSpeed
					Integer32,
				otxFansControl
					INTEGER,
				otxFansName
					DisplayString
			 }

--         1.3.6.1.4.1.1.1.7.5.1.1
-- 1.3.6.1.4.1.17409.1.7.5.1.1
-- 1.3.6.1.4.1.17409.1.7.5.1.1
-- 1.3.6.1.4.1.17409.1.7.5.1.1
-- 1.3.6.1.4.1.17409.1.7.5.1.1
-- 1.3.6.1.4.1.17409.1.7.5.1.1
-- 1.3.6.1.4.1.17409.1.7.5.1.1
-- 1.3.6.1.4.1.17409.1.7.5.1.1
		-- 1.3.6.1.4.1.17409.1.7.5.1.1
		otxFansIndex OBJECT-TYPE
			SYNTAX Integer32
			MAX-ACCESS read-only
			STATUS optional
			DESCRIPTION
				"散热风扇信息表索引。"
			::= { otxFansEntry 1 }

		
--         1.3.6.1.4.1.1.1.7.5.1.2
-- 1.3.6.1.4.1.17409.1.7.5.1.2
-- 1.3.6.1.4.1.17409.1.7.5.1.2
-- 1.3.6.1.4.1.17409.1.7.5.1.2
-- 1.3.6.1.4.1.17409.1.7.5.1.2
-- 1.3.6.1.4.1.17409.1.7.5.1.2
-- 1.3.6.1.4.1.17409.1.7.5.1.2
-- 1.3.6.1.4.1.17409.1.7.5.1.2
		-- 1.3.6.1.4.1.17409.1.7.5.1.2
		otxFansState OBJECT-TYPE
			SYNTAX INTEGER
				{
				normal(1),
				fault(2),
				off(3)
				}
			MAX-ACCESS read-only
			STATUS optional
			DESCRIPTION
				"散热风扇工作状态，normal 表示正常, fault 表示失效,off表示关闭。此对象要求在属性MIB中登记一个条目。"
			::= { otxFansEntry 2 }

		
--         1.3.6.1.4.1.1.1.7.5.1.3
-- 1.3.6.1.4.1.17409.1.7.5.1.3
-- 1.3.6.1.4.1.17409.1.7.5.1.3
-- 1.3.6.1.4.1.17409.1.7.5.1.3
-- 1.3.6.1.4.1.17409.1.7.5.1.3
-- 1.3.6.1.4.1.17409.1.7.5.1.3
-- 1.3.6.1.4.1.17409.1.7.5.1.3
-- 1.3.6.1.4.1.17409.1.7.5.1.3
		-- 1.3.6.1.4.1.17409.1.7.5.1.3
		otxFansSpeed OBJECT-TYPE
			SYNTAX Integer32
			MAX-ACCESS read-only
			STATUS optional
			DESCRIPTION
				"散热风扇工作时的转速，单位为转/分，不支持转速检测时可置为0。此对象要求在属性MIB中登记一个条目。"
			::= { otxFansEntry 3 }

		
--         1.3.6.1.4.1.1.1.7.5.1.4
-- 1.3.6.1.4.1.17409.1.7.5.1.4
-- 1.3.6.1.4.1.17409.1.7.5.1.4
-- 1.3.6.1.4.1.17409.1.7.5.1.4
-- 1.3.6.1.4.1.17409.1.7.5.1.4
-- 1.3.6.1.4.1.17409.1.7.5.1.4
-- 1.3.6.1.4.1.17409.1.7.5.1.4
-- 1.3.6.1.4.1.17409.1.7.5.1.4
		-- 1.3.6.1.4.1.17409.1.7.5.1.4
		otxFansControl OBJECT-TYPE
			SYNTAX INTEGER
				{
				on(1),
				off(2)
				}
			MAX-ACCESS read-write
			STATUS optional
			DESCRIPTION
				"散热风扇工作控制。 "
			::= { otxFansEntry 4 }

		
--         1.3.6.1.4.1.1.1.7.5.1.5
-- 1.3.6.1.4.1.17409.1.7.5.1.5
-- 1.3.6.1.4.1.17409.1.7.5.1.5
-- 1.3.6.1.4.1.17409.1.7.5.1.5
-- 1.3.6.1.4.1.17409.1.7.5.1.5
-- 1.3.6.1.4.1.17409.1.7.5.1.5
-- 1.3.6.1.4.1.17409.1.7.5.1.5
-- 1.3.6.1.4.1.17409.1.7.5.1.5
		-- 1.3.6.1.4.1.17409.1.7.5.1.5
		otxFansName OBJECT-TYPE
			SYNTAX DisplayString
			MAX-ACCESS read-only
			STATUS optional
			DESCRIPTION
				"散热风扇名称。"
			::= { otxFansEntry 5 }

		
--          *****************
-- * 直流电源
-- *****************
-- 1.3.6.1.4.1.1.1.7.6
-- 1.3.6.1.4.1.17409.1.7.6
-- 1.3.6.1.4.1.17409.1.7.6
-- 1.3.6.1.4.1.17409.1.7.6
-- 1.3.6.1.4.1.17409.1.7.6
-- 1.3.6.1.4.1.17409.1.7.6
-- 1.3.6.1.4.1.17409.1.7.6
-- 1.3.6.1.4.1.17409.1.7.6
		-- 1.3.6.1.4.1.17409.1.7.6
		otxNumberDCPowerSupply OBJECT-TYPE
			SYNTAX INTEGER (0..16)
			MAX-ACCESS read-only
			STATUS current
			DESCRIPTION
				"内部直流电源的数目，'0'表示设备不支持直流电源监测。"
			::= { otxIdent 6 }

		
--         1.3.6.1.4.1.1.1.7.7
-- 1.3.6.1.4.1.17409.1.7.7
-- 1.3.6.1.4.1.17409.1.7.7
-- 1.3.6.1.4.1.17409.1.7.7
-- 1.3.6.1.4.1.17409.1.7.7
-- 1.3.6.1.4.1.17409.1.7.7
-- 1.3.6.1.4.1.17409.1.7.7
-- 1.3.6.1.4.1.17409.1.7.7
		-- 1.3.6.1.4.1.17409.1.7.7
		otxDCPowerSupplyMode OBJECT-TYPE
			SYNTAX INTEGER
				{
				loadsharing(1),
				switchedRedundant(2),
				aloneSupply(3)
				}
			MAX-ACCESS read-only
			STATUS optional
			DESCRIPTION
				"供电电源工作模式包括负载分担、备用切换或独立供电三种。"
			::= { otxIdent 7 }

		
--         1.3.6.1.4.1.1.1.7.8
-- 1.3.6.1.4.1.17409.1.7.8
-- 1.3.6.1.4.1.17409.1.7.8
-- 1.3.6.1.4.1.17409.1.7.8
-- 1.3.6.1.4.1.17409.1.7.8
-- 1.3.6.1.4.1.17409.1.7.8
-- 1.3.6.1.4.1.17409.1.7.8
-- 1.3.6.1.4.1.17409.1.7.8
		-- 1.3.6.1.4.1.17409.1.7.8
		otxDCPowerTable OBJECT-TYPE
			SYNTAX SEQUENCE OF OtxDCPowerEntry
			MAX-ACCESS not-accessible
			STATUS current
			DESCRIPTION
				"直流电源信息表。"
			::= { otxIdent 8 }

		
--         1.3.6.1.4.1.1.1.7.8.1
-- 1.3.6.1.4.1.17409.1.7.8.1
-- 1.3.6.1.4.1.17409.1.7.8.1
-- 1.3.6.1.4.1.17409.1.7.8.1
-- 1.3.6.1.4.1.17409.1.7.8.1
-- 1.3.6.1.4.1.17409.1.7.8.1
-- 1.3.6.1.4.1.17409.1.7.8.1
-- 1.3.6.1.4.1.17409.1.7.8.1
		-- 1.3.6.1.4.1.17409.1.7.8.1
		otxDCPowerEntry OBJECT-TYPE
			SYNTAX OtxDCPowerEntry
			MAX-ACCESS not-accessible
			STATUS current
			DESCRIPTION
				"直流电源信息表目。"
			INDEX { otxDCPowerIndex }
			::= { otxDCPowerTable 1 }

		
		OtxDCPowerEntry ::=
			SEQUENCE { 
				otxDCPowerIndex
					Integer32,
				otxDCPowerVoltage
					INTEGER,
				otxDCPowerCurrent
					INTEGER,
				otxDCPowerName
					DisplayString
			 }

--         1.3.6.1.4.1.1.1.7.8.1.1
-- 1.3.6.1.4.1.17409.1.7.8.1.1
-- 1.3.6.1.4.1.17409.1.7.8.1.1
-- 1.3.6.1.4.1.17409.1.7.8.1.1
-- 1.3.6.1.4.1.17409.1.7.8.1.1
-- 1.3.6.1.4.1.17409.1.7.8.1.1
-- 1.3.6.1.4.1.17409.1.7.8.1.1
-- 1.3.6.1.4.1.17409.1.7.8.1.1
		-- 1.3.6.1.4.1.17409.1.7.8.1.1
		otxDCPowerIndex OBJECT-TYPE
			SYNTAX Integer32
			MAX-ACCESS read-only
			STATUS current
			DESCRIPTION
				"直流电源索引,表otxDCPowerTable的索引。"
			::= { otxDCPowerEntry 1 }

		
--         1.3.6.1.4.1.1.1.7.8.1.2
-- 1.3.6.1.4.1.17409.1.7.8.1.2
-- 1.3.6.1.4.1.17409.1.7.8.1.2
-- 1.3.6.1.4.1.17409.1.7.8.1.2
-- 1.3.6.1.4.1.17409.1.7.8.1.2
-- 1.3.6.1.4.1.17409.1.7.8.1.2
-- 1.3.6.1.4.1.17409.1.7.8.1.2
-- 1.3.6.1.4.1.17409.1.7.8.1.2
		-- 1.3.6.1.4.1.17409.1.7.8.1.2
		otxDCPowerVoltage OBJECT-TYPE
			SYNTAX INTEGER (-32768..32767)
			MAX-ACCESS read-only
			STATUS current
			DESCRIPTION
				"电源电压，单位为0.1V。此对象要求在属性MIB中登记一个条目。"
			::= { otxDCPowerEntry 2 }

		
--         1.3.6.1.4.1.1.1.7.8.1.3
-- 1.3.6.1.4.1.17409.1.7.8.1.3
-- 1.3.6.1.4.1.17409.1.7.8.1.3
-- 1.3.6.1.4.1.17409.1.7.8.1.3
-- 1.3.6.1.4.1.17409.1.7.8.1.3
-- 1.3.6.1.4.1.17409.1.7.8.1.3
-- 1.3.6.1.4.1.17409.1.7.8.1.3
-- 1.3.6.1.4.1.17409.1.7.8.1.3
		-- 1.3.6.1.4.1.17409.1.7.8.1.3
		otxDCPowerCurrent OBJECT-TYPE
			SYNTAX INTEGER (0..65535)
			MAX-ACCESS read-only
			STATUS optional
			DESCRIPTION
				"电源的电流，单位为0.1A。此对象要求在属性MIB中登记一个条目。"
			::= { otxDCPowerEntry 3 }

		
--         1.3.6.1.4.1.1.1.7.8.1.4
-- 1.3.6.1.4.1.17409.1.7.8.1.4
-- 1.3.6.1.4.1.17409.1.7.8.1.4
-- 1.3.6.1.4.1.17409.1.7.8.1.4
-- 1.3.6.1.4.1.17409.1.7.8.1.4
-- 1.3.6.1.4.1.17409.1.7.8.1.4
-- 1.3.6.1.4.1.17409.1.7.8.1.4
-- 1.3.6.1.4.1.17409.1.7.8.1.4
		-- 1.3.6.1.4.1.17409.1.7.8.1.4
		otxDCPowerName OBJECT-TYPE
			SYNTAX DisplayString
			MAX-ACCESS read-only
			STATUS current
			DESCRIPTION
				"标明直流电源名称，例如：24V直流电源。
				此字段值由用户规定，至少应标明工作电压并将多个电源相互区分开。
				当此表中的对象产生告警时，此对象名称应放进hfcAlarmEvent陷阱的alarmText对象里。"
			::= { otxDCPowerEntry 4 }

		
--              DESCRIPTION
-- "外调制光发送机MIB的分支节点标识。"
-- "见附录I。"
-- 1.3.6.1.4.1.1.1.8
-- 1.3.6.1.4.1.17409.1.8
-- 1.3.6.1.4.1.17409.1.8
-- 1.3.6.1.4.1.17409.1.8
-- 1.3.6.1.4.1.17409.1.8
-- 1.3.6.1.4.1.17409.1.8
-- 1.3.6.1.4.1.17409.1.8
-- 1.3.6.1.4.1.17409.1.8
		-- 1.3.6.1.4.1.17409.1.8
		uporIdent OBJECT IDENTIFIER ::= { nscrtvHFCemsTree 8 }

		
--         **********************************************************************************************
-- 上行光接收机MIB
-- **********************************************************************************************
-- 1.3.6.1.4.1.1.1.8.1
-- 1.3.6.1.4.1.17409.1.8.1
-- 1.3.6.1.4.1.17409.1.8.1
-- 1.3.6.1.4.1.17409.1.8.1
-- 1.3.6.1.4.1.17409.1.8.1
-- 1.3.6.1.4.1.17409.1.8.1
-- 1.3.6.1.4.1.17409.1.8.1
-- 1.3.6.1.4.1.17409.1.8.1
		-- 1.3.6.1.4.1.17409.1.8.1
		uporVendorOID OBJECT-TYPE
			SYNTAX OBJECT IDENTIFIER
			MAX-ACCESS read-only
			STATUS optional
			DESCRIPTION
				"此对象提供厂商对上行光接收机MIB的扩充，无扩充时此对象应指向上行光接收机节点uporIdent。"
			::= { uporIdent 1 }

		
--         1.3.6.1.4.1.1.1.8.2
-- 1.3.6.1.4.1.17409.1.8.2
-- 1.3.6.1.4.1.17409.1.8.2
-- 1.3.6.1.4.1.17409.1.8.2
-- 1.3.6.1.4.1.17409.1.8.2
-- 1.3.6.1.4.1.17409.1.8.2
-- 1.3.6.1.4.1.17409.1.8.2
-- 1.3.6.1.4.1.17409.1.8.2
		-- 1.3.6.1.4.1.17409.1.8.2
		uporSlotNumber OBJECT-TYPE
			SYNTAX INTEGER (0..32767)
			MAX-ACCESS read-only
			STATUS current
			DESCRIPTION
				"上行光接收机数量或机架插槽数量。"
			::= { uporIdent 2 }

		
--         1.3.6.1.4.1.1.1.8.3
-- 1.3.6.1.4.1.17409.1.8.3
-- 1.3.6.1.4.1.17409.1.8.3
-- 1.3.6.1.4.1.17409.1.8.3
-- 1.3.6.1.4.1.17409.1.8.3
-- 1.3.6.1.4.1.17409.1.8.3
-- 1.3.6.1.4.1.17409.1.8.3
-- 1.3.6.1.4.1.17409.1.8.3
		-- 1.3.6.1.4.1.17409.1.8.3
		uporDeviceTable OBJECT-TYPE
			SYNTAX SEQUENCE OF UporDeviceEntry
			MAX-ACCESS not-accessible
			STATUS current
			DESCRIPTION
				"上行光接收机信息表。"
			::= { uporIdent 3 }

		
--         1.3.6.1.4.1.1.1.8.3.1
-- 1.3.6.1.4.1.17409.1.8.3.1
-- 1.3.6.1.4.1.17409.1.8.3.1
-- 1.3.6.1.4.1.17409.1.8.3.1
-- 1.3.6.1.4.1.17409.1.8.3.1
-- 1.3.6.1.4.1.17409.1.8.3.1
-- 1.3.6.1.4.1.17409.1.8.3.1
-- 1.3.6.1.4.1.17409.1.8.3.1
		-- 1.3.6.1.4.1.17409.1.8.3.1
		uporDeviceEntry OBJECT-TYPE
			SYNTAX UporDeviceEntry
			MAX-ACCESS not-accessible
			STATUS current
			DESCRIPTION
				"上行光接收机信息表目。"
			INDEX { uporIndex }
			::= { uporDeviceTable 1 }

		
		UporDeviceEntry ::=
			SEQUENCE { 
				uporIndex
					INTEGER,
				uporOpicalInputPower
					INTEGER,
				uporOutputRFAttenuationRange
					INTEGER,
				uporOutputRFAttenuation
					INTEGER,
				uporAGCControl
					INTEGER
			 }

--         1.3.6.1.4.1.1.1.8.3.1.1
-- 1.3.6.1.4.1.17409.1.8.3.1.1
-- 1.3.6.1.4.1.17409.1.8.3.1.1
-- 1.3.6.1.4.1.17409.1.8.3.1.1
-- 1.3.6.1.4.1.17409.1.8.3.1.1
-- 1.3.6.1.4.1.17409.1.8.3.1.1
-- 1.3.6.1.4.1.17409.1.8.3.1.1
-- 1.3.6.1.4.1.17409.1.8.3.1.1
		-- 1.3.6.1.4.1.17409.1.8.3.1.1
		uporIndex OBJECT-TYPE
			SYNTAX INTEGER (0..32767)
			MAX-ACCESS read-only
			STATUS current
			DESCRIPTION
				"光接收机索引。"
			::= { uporDeviceEntry 1 }

		
--         1.3.6.1.4.1.1.1.8.3.1.2
-- 1.3.6.1.4.1.17409.1.8.3.1.2
-- 1.3.6.1.4.1.17409.1.8.3.1.2
-- 1.3.6.1.4.1.17409.1.8.3.1.2
-- 1.3.6.1.4.1.17409.1.8.3.1.2
-- 1.3.6.1.4.1.17409.1.8.3.1.2
-- 1.3.6.1.4.1.17409.1.8.3.1.2
-- 1.3.6.1.4.1.17409.1.8.3.1.2
		-- 1.3.6.1.4.1.17409.1.8.3.1.2
		uporOpicalInputPower OBJECT-TYPE
			SYNTAX INTEGER (-32768..32767)
			MAX-ACCESS read-only
			STATUS current
			DESCRIPTION
				"输入光功率,单位为0.1dBm。此对象要求在属性MIB中登记一个条目。"
			::= { uporDeviceEntry 2 }

		
--         1.3.6.1.4.1.1.1.8.3.1.3
-- 1.3.6.1.4.1.17409.1.8.3.1.3
-- 1.3.6.1.4.1.17409.1.8.3.1.3
-- 1.3.6.1.4.1.17409.1.8.3.1.3
-- 1.3.6.1.4.1.17409.1.8.3.1.3
-- 1.3.6.1.4.1.17409.1.8.3.1.3
-- 1.3.6.1.4.1.17409.1.8.3.1.3
-- 1.3.6.1.4.1.17409.1.8.3.1.3
		-- 1.3.6.1.4.1.17409.1.8.3.1.3
		uporOutputRFAttenuationRange OBJECT-TYPE
			SYNTAX INTEGER (0..127)
			MAX-ACCESS read-only
			STATUS optional
			DESCRIPTION
				"最大输出射频衰减量,单位为dB。"
			::= { uporDeviceEntry 3 }

		
--         1.3.6.1.4.1.1.1.8.3.1.4
-- 1.3.6.1.4.1.17409.1.8.3.1.4
-- 1.3.6.1.4.1.17409.1.8.3.1.4
-- 1.3.6.1.4.1.17409.1.8.3.1.4
-- 1.3.6.1.4.1.17409.1.8.3.1.4
-- 1.3.6.1.4.1.17409.1.8.3.1.4
-- 1.3.6.1.4.1.17409.1.8.3.1.4
-- 1.3.6.1.4.1.17409.1.8.3.1.4
		-- 1.3.6.1.4.1.17409.1.8.3.1.4
		uporOutputRFAttenuation OBJECT-TYPE
			SYNTAX INTEGER (0..127)
			MAX-ACCESS read-write
			STATUS optional
			DESCRIPTION
				"输出射频信号衰减量,单位为dB。"
			::= { uporDeviceEntry 4 }

		
--         1.3.6.1.4.1.1.1.8.3.1.5
-- 1.3.6.1.4.1.17409.1.8.3.1.5
-- 1.3.6.1.4.1.17409.1.8.3.1.5
-- 1.3.6.1.4.1.17409.1.8.3.1.5
-- 1.3.6.1.4.1.17409.1.8.3.1.5
-- 1.3.6.1.4.1.17409.1.8.3.1.5
-- 1.3.6.1.4.1.17409.1.8.3.1.5
-- 1.3.6.1.4.1.17409.1.8.3.1.5
		-- 1.3.6.1.4.1.17409.1.8.3.1.5
		uporAGCControl OBJECT-TYPE
			SYNTAX INTEGER
				{
				off(1),
				on(2)
				}
			MAX-ACCESS read-write
			STATUS optional
			DESCRIPTION
				"AGC控制使能。"
			::= { uporDeviceEntry 5 }

		
--         1.3.6.1.4.1.1.1.8.4
-- 1.3.6.1.4.1.17409.1.8.4
-- 1.3.6.1.4.1.17409.1.8.4
-- 1.3.6.1.4.1.17409.1.8.4
-- 1.3.6.1.4.1.17409.1.8.4
-- 1.3.6.1.4.1.17409.1.8.4
-- 1.3.6.1.4.1.17409.1.8.4
-- 1.3.6.1.4.1.17409.1.8.4
		-- 1.3.6.1.4.1.17409.1.8.4
		uporNumberDCPowerSupply OBJECT-TYPE
			SYNTAX INTEGER (0..16)
			MAX-ACCESS read-only
			STATUS current
			DESCRIPTION
				"直流电源数量，'0'表示应答器不支持此功能"
			::= { uporIdent 4 }

		
--         1.3.6.1.4.1.1.1.8.5
-- 1.3.6.1.4.1.17409.1.8.5
-- 1.3.6.1.4.1.17409.1.8.5
-- 1.3.6.1.4.1.17409.1.8.5
-- 1.3.6.1.4.1.17409.1.8.5
-- 1.3.6.1.4.1.17409.1.8.5
-- 1.3.6.1.4.1.17409.1.8.5
-- 1.3.6.1.4.1.17409.1.8.5
		-- 1.3.6.1.4.1.17409.1.8.5
		uporDCPowerSupplyMode OBJECT-TYPE
			SYNTAX INTEGER
				{
				loadsharing(1),
				switchedRedundant(2),
				aloneSupply(3)
				}
			MAX-ACCESS read-only
			STATUS optional
			DESCRIPTION
				"供电电源工作模式。"
			::= { uporIdent 5 }

		
--         1.3.6.1.4.1.1.1.8.6
-- 1.3.6.1.4.1.17409.1.8.6
-- 1.3.6.1.4.1.17409.1.8.6
-- 1.3.6.1.4.1.17409.1.8.6
-- 1.3.6.1.4.1.17409.1.8.6
-- 1.3.6.1.4.1.17409.1.8.6
-- 1.3.6.1.4.1.17409.1.8.6
-- 1.3.6.1.4.1.17409.1.8.6
		-- 1.3.6.1.4.1.17409.1.8.6
		uporDCPowerTable OBJECT-TYPE
			SYNTAX SEQUENCE OF UporDCPowerEntry
			MAX-ACCESS not-accessible
			STATUS current
			DESCRIPTION
				"直流电源信息表。"
			::= { uporIdent 6 }

		
--         1.3.6.1.4.1.1.1.8.6.1
-- 1.3.6.1.4.1.17409.1.8.6.1
-- 1.3.6.1.4.1.17409.1.8.6.1
-- 1.3.6.1.4.1.17409.1.8.6.1
-- 1.3.6.1.4.1.17409.1.8.6.1
-- 1.3.6.1.4.1.17409.1.8.6.1
-- 1.3.6.1.4.1.17409.1.8.6.1
-- 1.3.6.1.4.1.17409.1.8.6.1
		-- 1.3.6.1.4.1.17409.1.8.6.1
		uporDCPowerEntry OBJECT-TYPE
			SYNTAX UporDCPowerEntry
			MAX-ACCESS not-accessible
			STATUS current
			DESCRIPTION
				"直流电源信息表目。"
			INDEX { uporDCPowerIndex }
			::= { uporDCPowerTable 1 }

		
		UporDCPowerEntry ::=
			SEQUENCE { 
				uporDCPowerIndex
					Integer32,
				uporDCPowerVoltage
					INTEGER,
				uporDCPowerCurrent
					INTEGER,
				uporDCPowerName
					DisplayString
			 }

--         1.3.6.1.4.1.1.1.8.6.1.1
-- 1.3.6.1.4.1.17409.1.8.6.1.1
-- 1.3.6.1.4.1.17409.1.8.6.1.1
-- 1.3.6.1.4.1.17409.1.8.6.1.1
-- 1.3.6.1.4.1.17409.1.8.6.1.1
-- 1.3.6.1.4.1.17409.1.8.6.1.1
-- 1.3.6.1.4.1.17409.1.8.6.1.1
-- 1.3.6.1.4.1.17409.1.8.6.1.1
		-- 1.3.6.1.4.1.17409.1.8.6.1.1
		uporDCPowerIndex OBJECT-TYPE
			SYNTAX Integer32
			MAX-ACCESS read-only
			STATUS current
			DESCRIPTION
				"直流电源索引。"
			::= { uporDCPowerEntry 1 }

		
--         1.3.6.1.4.1.1.1.8.6.1.2
-- 1.3.6.1.4.1.17409.1.8.6.1.2
-- 1.3.6.1.4.1.17409.1.8.6.1.2
-- 1.3.6.1.4.1.17409.1.8.6.1.2
-- 1.3.6.1.4.1.17409.1.8.6.1.2
-- 1.3.6.1.4.1.17409.1.8.6.1.2
-- 1.3.6.1.4.1.17409.1.8.6.1.2
-- 1.3.6.1.4.1.17409.1.8.6.1.2
		-- 1.3.6.1.4.1.17409.1.8.6.1.2
		uporDCPowerVoltage OBJECT-TYPE
			SYNTAX INTEGER (-32768..32767)
			MAX-ACCESS read-only
			STATUS current
			DESCRIPTION
				"电源电压，单位为0.1V。此对象要求在属性MIB中登记一个条目。"
			::= { uporDCPowerEntry 2 }

		
--         1.3.6.1.4.1.1.1.8.6.1.3
-- 1.3.6.1.4.1.17409.1.8.6.1.3
-- 1.3.6.1.4.1.17409.1.8.6.1.3
-- 1.3.6.1.4.1.17409.1.8.6.1.3
-- 1.3.6.1.4.1.17409.1.8.6.1.3
-- 1.3.6.1.4.1.17409.1.8.6.1.3
-- 1.3.6.1.4.1.17409.1.8.6.1.3
-- 1.3.6.1.4.1.17409.1.8.6.1.3
		-- 1.3.6.1.4.1.17409.1.8.6.1.3
		uporDCPowerCurrent OBJECT-TYPE
			SYNTAX INTEGER (0..65535)
			MAX-ACCESS read-only
			STATUS optional
			DESCRIPTION
				"电源的电流，单位为0.1A。此对象要求在属性MIB中登记一个条目。"
			::= { uporDCPowerEntry 3 }

		
--         1.3.6.1.4.1.1.1.8.6.1.4
-- 1.3.6.1.4.1.17409.1.8.6.1.4
-- 1.3.6.1.4.1.17409.1.8.6.1.4
-- 1.3.6.1.4.1.17409.1.8.6.1.4
-- 1.3.6.1.4.1.17409.1.8.6.1.4
-- 1.3.6.1.4.1.17409.1.8.6.1.4
-- 1.3.6.1.4.1.17409.1.8.6.1.4
-- 1.3.6.1.4.1.17409.1.8.6.1.4
		-- 1.3.6.1.4.1.17409.1.8.6.1.4
		uporDCPowerName OBJECT-TYPE
			SYNTAX DisplayString
			MAX-ACCESS read-only
			STATUS current
			DESCRIPTION
				"标明电源的名称，例如：24V直流电源。
				此字段值由用户规定，至少应标明工作电压并将多个电源相互区分开。
				当表中的对象产生告警时，此对象名称应放进hfcAlarmEvent陷阱的alarmText对象里（见附录D）。"
			::= { uporDCPowerEntry 4 }

		
--              DESCRIPTION
-- "上行光接收机(UpStream Optical Receiver)MIB的分支节点标识。"
-- "见附录J。"
-- 1.3.6.1.4.1.1.1.9
-- 1.3.6.1.4.1.17409.1.9
-- 1.3.6.1.4.1.17409.1.9
-- 1.3.6.1.4.1.17409.1.9
-- 1.3.6.1.4.1.17409.1.9
-- 1.3.6.1.4.1.17409.1.9
-- 1.3.6.1.4.1.17409.1.9
-- 1.3.6.1.4.1.17409.1.9
		-- 1.3.6.1.4.1.17409.1.9
		dorIdent OBJECT IDENTIFIER ::= { nscrtvHFCemsTree 9 }

		
--         *********************************************************************************************
-- 下行光接收机MIB
-- *********************************************************************************************
-- 1.3.6.1.4.1.1.1.9.1
-- 1.3.6.1.4.1.17409.1.9.1
-- 1.3.6.1.4.1.17409.1.9.1
-- 1.3.6.1.4.1.17409.1.9.1
-- 1.3.6.1.4.1.17409.1.9.1
-- 1.3.6.1.4.1.17409.1.9.1
-- 1.3.6.1.4.1.17409.1.9.1
-- 1.3.6.1.4.1.17409.1.9.1
		-- 1.3.6.1.4.1.17409.1.9.1
		dorVendorOID OBJECT-TYPE
			SYNTAX OBJECT IDENTIFIER
			MAX-ACCESS read-only
			STATUS optional
			DESCRIPTION
				"此对象提供厂商对下行光接收机MIB的扩充，无扩充时此对象应指向下行光接收机节点dorIdent。"
			::= { dorIdent 1 }

		
--         1.3.6.1.4.1.1.1.9.2
-- 1.3.6.1.4.1.17409.1.9.2
-- 1.3.6.1.4.1.17409.1.9.2
-- 1.3.6.1.4.1.17409.1.9.2
-- 1.3.6.1.4.1.17409.1.9.2
-- 1.3.6.1.4.1.17409.1.9.2
-- 1.3.6.1.4.1.17409.1.9.2
-- 1.3.6.1.4.1.17409.1.9.2
		-- 1.3.6.1.4.1.17409.1.9.2
		opRxInputNumber OBJECT-TYPE
			SYNTAX Integer32
			MAX-ACCESS read-only
			STATUS current
			DESCRIPTION
				"下行光接收机中光输入部分的数量，一般为'1'。 "
			::= { dorIdent 2 }

		
--         1.3.6.1.4.1.1.1.9.3
-- 1.3.6.1.4.1.17409.1.9.3
-- 1.3.6.1.4.1.17409.1.9.3
-- 1.3.6.1.4.1.17409.1.9.3
-- 1.3.6.1.4.1.17409.1.9.3
-- 1.3.6.1.4.1.17409.1.9.3
-- 1.3.6.1.4.1.17409.1.9.3
-- 1.3.6.1.4.1.17409.1.9.3
		-- 1.3.6.1.4.1.17409.1.9.3
		opRxInputTable OBJECT-TYPE
			SYNTAX SEQUENCE OF OpRxInputEntry
			MAX-ACCESS not-accessible
			STATUS current
			DESCRIPTION
				"下行光接收机中每一个光部分的信息表。"
			::= { dorIdent 3 }

		
--         1.3.6.1.4.1.1.1.9.3.1
-- 1.3.6.1.4.1.17409.1.9.3.1
-- 1.3.6.1.4.1.17409.1.9.3.1
-- 1.3.6.1.4.1.17409.1.9.3.1
-- 1.3.6.1.4.1.17409.1.9.3.1
-- 1.3.6.1.4.1.17409.1.9.3.1
-- 1.3.6.1.4.1.17409.1.9.3.1
-- 1.3.6.1.4.1.17409.1.9.3.1
		-- 1.3.6.1.4.1.17409.1.9.3.1
		opRxInputEntry OBJECT-TYPE
			SYNTAX OpRxInputEntry
			MAX-ACCESS not-accessible
			STATUS current
			DESCRIPTION
				"下行光接收机中每一个光部分的信息列表。"
			INDEX { dorInputIndex }
			::= { opRxInputTable 1 }

		
		OpRxInputEntry ::=
			SEQUENCE { 
				dorInputIndex
					Integer32,
				dorInputPower
					OCTET STRING,
				dorInputWavelengthControl
					Integer32,
				dorInputStatus
					INTEGER
			 }

--         1.3.6.1.4.1.1.1.9.3.1.1
-- 1.3.6.1.4.1.17409.1.9.3.1.1
-- 1.3.6.1.4.1.17409.1.9.3.1.1
-- 1.3.6.1.4.1.17409.1.9.3.1.1
-- 1.3.6.1.4.1.17409.1.9.3.1.1
-- 1.3.6.1.4.1.17409.1.9.3.1.1
-- 1.3.6.1.4.1.17409.1.9.3.1.1
-- 1.3.6.1.4.1.17409.1.9.3.1.1
		-- 1.3.6.1.4.1.17409.1.9.3.1.1
		dorInputIndex OBJECT-TYPE
			SYNTAX Integer32
			MAX-ACCESS read-only
			STATUS current
			DESCRIPTION
				"一个正整数，用于唯一标识下行光接收机中的光输入。"
			::= { opRxInputEntry 1 }

		
--         1.3.6.1.4.1.1.1.9.3.1.2
-- 1.3.6.1.4.1.17409.1.9.3.1.2
-- 1.3.6.1.4.1.17409.1.9.3.1.2
-- 1.3.6.1.4.1.17409.1.9.3.1.2
-- 1.3.6.1.4.1.17409.1.9.3.1.2
-- 1.3.6.1.4.1.17409.1.9.3.1.2
-- 1.3.6.1.4.1.17409.1.9.3.1.2
-- 1.3.6.1.4.1.17409.1.9.3.1.2
		-- 1.3.6.1.4.1.17409.1.9.3.1.2
		dorInputPower OBJECT-TYPE
			SYNTAX OCTET STRING
			MAX-ACCESS read-only
			STATUS current
			DESCRIPTION
				"下行光接收机输入光功率，单位为0.1 mW。
				此对象要求在属性MIB中登记一个条目。"
			::= { opRxInputEntry 2 }

		
--         1.3.6.1.4.1.1.1.9.3.1.3
-- 1.3.6.1.4.1.17409.1.9.3.1.3
-- 1.3.6.1.4.1.17409.1.9.3.1.3
-- 1.3.6.1.4.1.17409.1.9.3.1.3
-- 1.3.6.1.4.1.17409.1.9.3.1.3
-- 1.3.6.1.4.1.17409.1.9.3.1.3
-- 1.3.6.1.4.1.17409.1.9.3.1.3
-- 1.3.6.1.4.1.17409.1.9.3.1.3
		-- 1.3.6.1.4.1.17409.1.9.3.1.3
		dorInputWavelengthControl OBJECT-TYPE
			SYNTAX Integer32
			MAX-ACCESS read-write
			STATUS current
			DESCRIPTION
				"下行光接收机接收光信号的波长，单位为1 nm。
				典型值为 1310 和 1550，分别表示接收光信号的波长为1310nm 和 1550nm。
				此对象可用于校正输入光功率的测量。"
			::= { opRxInputEntry 3 }

		
--         1.3.6.1.4.1.1.1.9.3.1.4
-- 1.3.6.1.4.1.17409.1.9.3.1.4
-- 1.3.6.1.4.1.17409.1.9.3.1.4
-- 1.3.6.1.4.1.17409.1.9.3.1.4
-- 1.3.6.1.4.1.17409.1.9.3.1.4
-- 1.3.6.1.4.1.17409.1.9.3.1.4
-- 1.3.6.1.4.1.17409.1.9.3.1.4
-- 1.3.6.1.4.1.17409.1.9.3.1.4
		-- 1.3.6.1.4.1.17409.1.9.3.1.4
		dorInputStatus OBJECT-TYPE
			SYNTAX INTEGER
				{
				normal(1),
				fault(2)
				}
			MAX-ACCESS read-only
			STATUS current
			DESCRIPTION
				"下行光接收机输入光功率检测器状态，normal表示接收光功率正常，fault表示接收光功率异常。
				此对象要求在属性MIB中登记一个条目。"
			::= { opRxInputEntry 4 }

		
--         1.3.6.1.4.1.1.1.9.4
-- 1.3.6.1.4.1.17409.1.9.4
-- 1.3.6.1.4.1.17409.1.9.4
-- 1.3.6.1.4.1.17409.1.9.4
-- 1.3.6.1.4.1.17409.1.9.4
-- 1.3.6.1.4.1.17409.1.9.4
-- 1.3.6.1.4.1.17409.1.9.4
-- 1.3.6.1.4.1.17409.1.9.4
		-- 1.3.6.1.4.1.17409.1.9.4
		opRxOutputNumber OBJECT-TYPE
			SYNTAX Integer32
			MAX-ACCESS read-only
			STATUS current
			DESCRIPTION
				"下行光接收机RF输出端口数。"
			::= { dorIdent 4 }

		
--         1.3.6.1.4.1.1.1.9.5
-- 1.3.6.1.4.1.17409.1.9.5
-- 1.3.6.1.4.1.17409.1.9.5
-- 1.3.6.1.4.1.17409.1.9.5
-- 1.3.6.1.4.1.17409.1.9.5
-- 1.3.6.1.4.1.17409.1.9.5
-- 1.3.6.1.4.1.17409.1.9.5
-- 1.3.6.1.4.1.17409.1.9.5
		-- 1.3.6.1.4.1.17409.1.9.5
		opRxOutputTable OBJECT-TYPE
			SYNTAX SEQUENCE OF OpRxOutputEntry
			MAX-ACCESS not-accessible
			STATUS current
			DESCRIPTION
				"下行光接收机输出RF信息表。"
			::= { dorIdent 5 }

		
--         1.3.6.1.4.1.1.1.9.5.1
-- 1.3.6.1.4.1.17409.1.9.5.1
-- 1.3.6.1.4.1.17409.1.9.5.1
-- 1.3.6.1.4.1.17409.1.9.5.1
-- 1.3.6.1.4.1.17409.1.9.5.1
-- 1.3.6.1.4.1.17409.1.9.5.1
-- 1.3.6.1.4.1.17409.1.9.5.1
-- 1.3.6.1.4.1.17409.1.9.5.1
		-- 1.3.6.1.4.1.17409.1.9.5.1
		opRxOutputEntry OBJECT-TYPE
			SYNTAX OpRxOutputEntry
			MAX-ACCESS not-accessible
			STATUS current
			DESCRIPTION
				"下行光接收机输出RF信息表目。"
			INDEX { dorOutputIndex }
			::= { opRxOutputTable 1 }

		
		OpRxOutputEntry ::=
			SEQUENCE { 
				dorOutputIndex
					Integer32,
				dorOutputControl
					INTEGER,
				dorOutputGainType
					INTEGER,
				dorOutputLevel
					OCTET STRING,
				dorConfigurationOutputLevel
					Integer32,
				dorOutputRFlevelatt
					Integer32,
				dorConfigurationOutputRFlevelatt
					Integer32,
				dorOutputRFName
					DisplayString
			 }

--         	dorOutputIndex
-- INTEGER,
-- dorOutputControl
-- INTEGER,
-- dorOutputGainType
-- INTEGER,
-- dorOutputLevel
-- INTEGER,
-- dorOutputRFPadlevel            
-- INTEGER,
-- dorOutputRFName
-- DisplayString    
-- 1.3.6.1.4.1.1.1.9.5.1.1
-- 1.3.6.1.4.1.17409.1.9.5.1.1
-- 1.3.6.1.4.1.17409.1.9.5.1.1
-- 1.3.6.1.4.1.17409.1.9.5.1.1
-- 1.3.6.1.4.1.17409.1.9.5.1.1
-- 1.3.6.1.4.1.17409.1.9.5.1.1
-- 1.3.6.1.4.1.17409.1.9.5.1.1
-- 1.3.6.1.4.1.17409.1.9.5.1.1
		-- 1.3.6.1.4.1.17409.1.9.5.1.1
		dorOutputIndex OBJECT-TYPE
			SYNTAX Integer32
			MAX-ACCESS read-only
			STATUS current
			DESCRIPTION
				"索引，即一个正整数，用于唯一标识下行光接收机中的一个输出。"
			::= { opRxOutputEntry 1 }

		
--         1.3.6.1.4.1.1.1.9.5.1.2
-- 1.3.6.1.4.1.17409.1.9.5.1.2
-- 1.3.6.1.4.1.17409.1.9.5.1.2
-- 1.3.6.1.4.1.17409.1.9.5.1.2
-- 1.3.6.1.4.1.17409.1.9.5.1.2
-- 1.3.6.1.4.1.17409.1.9.5.1.2
-- 1.3.6.1.4.1.17409.1.9.5.1.2
-- 1.3.6.1.4.1.17409.1.9.5.1.2
		-- 1.3.6.1.4.1.17409.1.9.5.1.2
		dorOutputControl OBJECT-TYPE
			SYNTAX INTEGER
				{
				off(1),
				on(2)
				}
			MAX-ACCESS read-write
			STATUS current
			DESCRIPTION
				"控制下行光接收机输出的开关。"
			::= { opRxOutputEntry 2 }

		
--         1.3.6.1.4.1.1.1.9.5.1.3
-- 1.3.6.1.4.1.17409.1.9.5.1.3
-- 1.3.6.1.4.1.17409.1.9.5.1.3
-- 1.3.6.1.4.1.17409.1.9.5.1.3
-- 1.3.6.1.4.1.17409.1.9.5.1.3
-- 1.3.6.1.4.1.17409.1.9.5.1.3
-- 1.3.6.1.4.1.17409.1.9.5.1.3
-- 1.3.6.1.4.1.17409.1.9.5.1.3
		-- 1.3.6.1.4.1.17409.1.9.5.1.3
		dorOutputGainType OBJECT-TYPE
			SYNTAX INTEGER
				{
				constantLevel(1),
				constantGain(2)
				}
			MAX-ACCESS read-write
			STATUS optional
			DESCRIPTION
				"控制下行光接收机输出增益的类型。constantLevel为恒定输出电平，constantGain为恒定信道增益，一般下行光接机都为恒定信道增益。"
			::= { opRxOutputEntry 3 }

		
--         1.3.6.1.4.1.1.1.9.5.1.4
-- 1.3.6.1.4.1.17409.1.9.5.1.4
-- 1.3.6.1.4.1.17409.1.9.5.1.4
-- 1.3.6.1.4.1.17409.1.9.5.1.4
-- 1.3.6.1.4.1.17409.1.9.5.1.4
-- 1.3.6.1.4.1.17409.1.9.5.1.4
-- 1.3.6.1.4.1.17409.1.9.5.1.4
-- 1.3.6.1.4.1.17409.1.9.5.1.4
		-- 1.3.6.1.4.1.17409.1.9.5.1.4
		dorOutputLevel OBJECT-TYPE
			SYNTAX OCTET STRING
			MAX-ACCESS read-only
			STATUS current
			DESCRIPTION
				"下行光接收机输出RF电平，单位为0.1dBuv。
				此对象要求在属性MIB中登记一个条目。"
			::= { opRxOutputEntry 4 }

		
--         1.3.6.1.4.1.1.1.9.5.1.5
-- 1.3.6.1.4.1.17409.1.9.5.1.5
-- 1.3.6.1.4.1.17409.1.9.5.1.5
-- 1.3.6.1.4.1.17409.1.9.5.1.5
-- 1.3.6.1.4.1.17409.1.9.5.1.5
-- 1.3.6.1.4.1.17409.1.9.5.1.5
-- 1.3.6.1.4.1.17409.1.9.5.1.5
-- 1.3.6.1.4.1.17409.1.9.5.1.5
		-- 1.3.6.1.4.1.17409.1.9.5.1.5
		dorConfigurationOutputLevel OBJECT-TYPE
			SYNTAX Integer32
			MAX-ACCESS read-write
			STATUS optional
			DESCRIPTION
				"下行光接收机输出RF电平设置，单位为0.1dBuv。当dorOutputGainType 参数为'1'时，本参数设置有效。"
			::= { opRxOutputEntry 5 }

		
--         1.3.6.1.4.1.1.1.9.5.1.6
-- 1.3.6.1.4.1.17409.1.9.5.1.6
-- 1.3.6.1.4.1.17409.1.9.5.1.6
-- 1.3.6.1.4.1.17409.1.9.5.1.6
-- 1.3.6.1.4.1.17409.1.9.5.1.6
-- 1.3.6.1.4.1.17409.1.9.5.1.6
-- 1.3.6.1.4.1.17409.1.9.5.1.6
-- 1.3.6.1.4.1.17409.1.9.5.1.6
		-- 1.3.6.1.4.1.17409.1.9.5.1.6
		dorOutputRFlevelatt OBJECT-TYPE
			SYNTAX Integer32
			MAX-ACCESS read-write
			STATUS current
			DESCRIPTION
				"下行光接收机中RF输出电平衰减量，单位为0.1dB。"
			::= { opRxOutputEntry 6 }

		
--         1.3.6.1.4.1.1.1.9.5.1.7
-- 1.3.6.1.4.1.17409.1.9.5.1.7
-- 1.3.6.1.4.1.17409.1.9.5.1.7
-- 1.3.6.1.4.1.17409.1.9.5.1.7
-- 1.3.6.1.4.1.17409.1.9.5.1.7
-- 1.3.6.1.4.1.17409.1.9.5.1.7
-- 1.3.6.1.4.1.17409.1.9.5.1.7
-- 1.3.6.1.4.1.17409.1.9.5.1.7
		-- 1.3.6.1.4.1.17409.1.9.5.1.7
		dorConfigurationOutputRFlevelatt OBJECT-TYPE
			SYNTAX Integer32
			MAX-ACCESS read-write
			STATUS optional
			DESCRIPTION
				"下行光接收机中RF输出电平衰减量设置，单位为0.1dB。当dorOutputGainType 参数为'2'时，本参数设置有效。"
			::= { opRxOutputEntry 7 }

		
--         1.3.6.1.4.1.1.1.9.5.1.8
-- 1.3.6.1.4.1.17409.1.9.5.1.8
-- 1.3.6.1.4.1.17409.1.9.5.1.8
-- 1.3.6.1.4.1.17409.1.9.5.1.8
-- 1.3.6.1.4.1.17409.1.9.5.1.8
-- 1.3.6.1.4.1.17409.1.9.5.1.8
-- 1.3.6.1.4.1.17409.1.9.5.1.8
-- 1.3.6.1.4.1.17409.1.9.5.1.8
		-- 1.3.6.1.4.1.17409.1.9.5.1.8
		dorOutputRFName OBJECT-TYPE
			SYNTAX DisplayString
			MAX-ACCESS read-only
			STATUS current
			DESCRIPTION
				"下行光接收机RF输出端口的名称。"
			::= { opRxOutputEntry 8 }

		
--          *****************
-- * 直流电源
-- *****************
-- 1.3.6.1.4.1.1.1.9.6
-- 1.3.6.1.4.1.17409.1.9.6
-- 1.3.6.1.4.1.17409.1.9.6
-- 1.3.6.1.4.1.17409.1.9.6
-- 1.3.6.1.4.1.17409.1.9.6
-- 1.3.6.1.4.1.17409.1.9.6
-- 1.3.6.1.4.1.17409.1.9.6
-- 1.3.6.1.4.1.17409.1.9.6
		-- 1.3.6.1.4.1.17409.1.9.6
		dorNumberDCPowerSupply OBJECT-TYPE
			SYNTAX INTEGER (0..16)
			MAX-ACCESS read-only
			STATUS current
			DESCRIPTION
				"内部直流电源的数目，'0'表示设备不支持直流电源监测。"
			::= { dorIdent 6 }

		
--         1.3.6.1.4.1.1.1.9.7
-- 1.3.6.1.4.1.17409.1.9.7
-- 1.3.6.1.4.1.17409.1.9.7
-- 1.3.6.1.4.1.17409.1.9.7
-- 1.3.6.1.4.1.17409.1.9.7
-- 1.3.6.1.4.1.17409.1.9.7
-- 1.3.6.1.4.1.17409.1.9.7
-- 1.3.6.1.4.1.17409.1.9.7
		-- 1.3.6.1.4.1.17409.1.9.7
		dorDCPowerSupplyMode OBJECT-TYPE
			SYNTAX INTEGER
				{
				loadsharing(1),
				switchedRedundant(2),
				aloneSupply(3)
				}
			MAX-ACCESS read-only
			STATUS optional
			DESCRIPTION
				"供电电源工作模式：负载分担、备用切换或独立供电。"
			::= { dorIdent 7 }

		
--         1.3.6.1.4.1.1.1.9.8
-- 1.3.6.1.4.1.17409.1.9.8
-- 1.3.6.1.4.1.17409.1.9.8
-- 1.3.6.1.4.1.17409.1.9.8
-- 1.3.6.1.4.1.17409.1.9.8
-- 1.3.6.1.4.1.17409.1.9.8
-- 1.3.6.1.4.1.17409.1.9.8
-- 1.3.6.1.4.1.17409.1.9.8
		-- 1.3.6.1.4.1.17409.1.9.8
		dorDCPowerTable OBJECT-TYPE
			SYNTAX SEQUENCE OF DorDCPowerEntry
			MAX-ACCESS not-accessible
			STATUS current
			DESCRIPTION
				"直流电源信息表。"
			::= { dorIdent 8 }

		
--         1.3.6.1.4.1.1.1.9.8.1
-- 1.3.6.1.4.1.17409.1.9.8.1
-- 1.3.6.1.4.1.17409.1.9.8.1
-- 1.3.6.1.4.1.17409.1.9.8.1
-- 1.3.6.1.4.1.17409.1.9.8.1
-- 1.3.6.1.4.1.17409.1.9.8.1
-- 1.3.6.1.4.1.17409.1.9.8.1
-- 1.3.6.1.4.1.17409.1.9.8.1
		-- 1.3.6.1.4.1.17409.1.9.8.1
		dorDCPowerEntry OBJECT-TYPE
			SYNTAX DorDCPowerEntry
			MAX-ACCESS not-accessible
			STATUS current
			DESCRIPTION
				"直流电源信息表目。"
			INDEX { dorDCPowerIndex }
			::= { dorDCPowerTable 1 }

		
		DorDCPowerEntry ::=
			SEQUENCE { 
				dorDCPowerIndex
					Integer32,
				dorDCPowerVoltage
					INTEGER,
				dorDCPowerCurrent
					INTEGER,
				dorDCPowerName
					DisplayString
			 }

--         1.3.6.1.4.1.1.1.9.8.1.1
-- 1.3.6.1.4.1.17409.1.9.8.1.1
-- 1.3.6.1.4.1.17409.1.9.8.1.1
-- 1.3.6.1.4.1.17409.1.9.8.1.1
-- 1.3.6.1.4.1.17409.1.9.8.1.1
-- 1.3.6.1.4.1.17409.1.9.8.1.1
-- 1.3.6.1.4.1.17409.1.9.8.1.1
-- 1.3.6.1.4.1.17409.1.9.8.1.1
		-- 1.3.6.1.4.1.17409.1.9.8.1.1
		dorDCPowerIndex OBJECT-TYPE
			SYNTAX Integer32
			MAX-ACCESS read-only
			STATUS current
			DESCRIPTION
				"直流电源索引,表dorDCPowerTable的索引。"
			::= { dorDCPowerEntry 1 }

		
--         1.3.6.1.4.1.1.1.9.8.1.2
-- 1.3.6.1.4.1.17409.1.9.8.1.2
-- 1.3.6.1.4.1.17409.1.9.8.1.2
-- 1.3.6.1.4.1.17409.1.9.8.1.2
-- 1.3.6.1.4.1.17409.1.9.8.1.2
-- 1.3.6.1.4.1.17409.1.9.8.1.2
-- 1.3.6.1.4.1.17409.1.9.8.1.2
-- 1.3.6.1.4.1.17409.1.9.8.1.2
		-- 1.3.6.1.4.1.17409.1.9.8.1.2
		dorDCPowerVoltage OBJECT-TYPE
			SYNTAX INTEGER (-32768..32767)
			MAX-ACCESS read-only
			STATUS current
			DESCRIPTION
				"电源电压，单位为0.1V，此对象要求在属性MIB中登记一个条目。"
			::= { dorDCPowerEntry 2 }

		
--         1.3.6.1.4.1.1.1.9.8.1.3
-- 1.3.6.1.4.1.17409.1.9.8.1.3
-- 1.3.6.1.4.1.17409.1.9.8.1.3
-- 1.3.6.1.4.1.17409.1.9.8.1.3
-- 1.3.6.1.4.1.17409.1.9.8.1.3
-- 1.3.6.1.4.1.17409.1.9.8.1.3
-- 1.3.6.1.4.1.17409.1.9.8.1.3
-- 1.3.6.1.4.1.17409.1.9.8.1.3
		-- 1.3.6.1.4.1.17409.1.9.8.1.3
		dorDCPowerCurrent OBJECT-TYPE
			SYNTAX INTEGER (0..65535)
			MAX-ACCESS read-only
			STATUS optional
			DESCRIPTION
				"电源的电流，单位为0.1A。此对象要求在属性MIB中登记一个条目。"
			::= { dorDCPowerEntry 3 }

		
--         1.3.6.1.4.1.1.1.9.8.1.4
-- 1.3.6.1.4.1.17409.1.9.8.1.4
-- 1.3.6.1.4.1.17409.1.9.8.1.4
-- 1.3.6.1.4.1.17409.1.9.8.1.4
-- 1.3.6.1.4.1.17409.1.9.8.1.4
-- 1.3.6.1.4.1.17409.1.9.8.1.4
-- 1.3.6.1.4.1.17409.1.9.8.1.4
-- 1.3.6.1.4.1.17409.1.9.8.1.4
		-- 1.3.6.1.4.1.17409.1.9.8.1.4
		dorDCPowerName OBJECT-TYPE
			SYNTAX DisplayString
			MAX-ACCESS read-only
			STATUS current
			DESCRIPTION
				"标明直流电源名称，例如：24V直流电源。
				此字段值由用户规定，至少应标明工作电压并将多个电源相互区分开。
				当此表中的对象产生告警时，此对象名称应放进hfcAlarmEvent陷阱的alarmText对象里。"
			::= { dorDCPowerEntry 4 }

		
--              DESCRIPTION
-- "下行光接收机（DownStream Optical Receiver）MIB的分支节点标识符。"
-- "见附录K。"
-- 1.3.6.1.4.1.1.1.10
-- 1.3.6.1.4.1.17409.1.10
-- 1.3.6.1.4.1.17409.1.10
-- 1.3.6.1.4.1.17409.1.10
-- 1.3.6.1.4.1.17409.1.10
-- 1.3.6.1.4.1.17409.1.10
-- 1.3.6.1.4.1.17409.1.10
-- 1.3.6.1.4.1.17409.1.10
		-- 1.3.6.1.4.1.17409.1.10
		fnIdent OBJECT IDENTIFIER ::= { nscrtvHFCemsTree 10 }

		
--         **********************************************************************************************
-- 光节点MIB
-- **********************************************************************************************
-- 1.3.6.1.4.1.1.1.10.1
-- 1.3.6.1.4.1.17409.1.10.1
-- 1.3.6.1.4.1.17409.1.10.1
-- 1.3.6.1.4.1.17409.1.10.1
-- 1.3.6.1.4.1.17409.1.10.1
-- 1.3.6.1.4.1.17409.1.10.1
-- 1.3.6.1.4.1.17409.1.10.1
-- 1.3.6.1.4.1.17409.1.10.1
		-- 1.3.6.1.4.1.17409.1.10.1
		fnVendorOID OBJECT-TYPE
			SYNTAX OBJECT IDENTIFIER
			MAX-ACCESS read-only
			STATUS optional
			DESCRIPTION
				"此对象提供厂商对光节点MIB的扩充，无扩充时此对象应指向光节点fnIdent。"
			::= { fnIdent 1 }

		
--          ****************
-- * 上行光发送机
-- ****************
-- 1.3.6.1.4.1.1.1.10.2
-- 1.3.6.1.4.1.17409.1.10.2
-- 1.3.6.1.4.1.17409.1.10.2
-- 1.3.6.1.4.1.17409.1.10.2
-- 1.3.6.1.4.1.17409.1.10.2
-- 1.3.6.1.4.1.17409.1.10.2
-- 1.3.6.1.4.1.17409.1.10.2
-- 1.3.6.1.4.1.17409.1.10.2
		-- 1.3.6.1.4.1.17409.1.10.2
		fnNumberReturnLaser OBJECT-TYPE
			SYNTAX INTEGER (0..16)
			MAX-ACCESS read-only
			STATUS current
			DESCRIPTION
				"光节点上行光发送机信息表的条目数，'0'表示设备无此功能。"
			::= { fnIdent 2 }

		
--         1.3.6.1.4.1.1.1.10.3
-- 1.3.6.1.4.1.17409.1.10.3
-- 1.3.6.1.4.1.17409.1.10.3
-- 1.3.6.1.4.1.17409.1.10.3
-- 1.3.6.1.4.1.17409.1.10.3
-- 1.3.6.1.4.1.17409.1.10.3
-- 1.3.6.1.4.1.17409.1.10.3
-- 1.3.6.1.4.1.17409.1.10.3
		-- 1.3.6.1.4.1.17409.1.10.3
		fnReturnLaserTable OBJECT-TYPE
			SYNTAX SEQUENCE OF FnReturnLaserEntry
			MAX-ACCESS not-accessible
			STATUS current
			DESCRIPTION
				"光节点上行光发送机信息表。"
			::= { fnIdent 3 }

		
--         1.3.6.1.4.1.1.1.10.3.1
-- 1.3.6.1.4.1.17409.1.10.3.1
-- 1.3.6.1.4.1.17409.1.10.3.1
-- 1.3.6.1.4.1.17409.1.10.3.1
-- 1.3.6.1.4.1.17409.1.10.3.1
-- 1.3.6.1.4.1.17409.1.10.3.1
-- 1.3.6.1.4.1.17409.1.10.3.1
-- 1.3.6.1.4.1.17409.1.10.3.1
		-- 1.3.6.1.4.1.17409.1.10.3.1
		fnReturnLaserEntry OBJECT-TYPE
			SYNTAX FnReturnLaserEntry
			MAX-ACCESS not-accessible
			STATUS current
			DESCRIPTION
				"上行光发送机表目。"
			INDEX { fnReturnLaserIndex }
			::= { fnReturnLaserTable 1 }

		
		FnReturnLaserEntry ::=
			SEQUENCE { 
				fnReturnLaserIndex
					Integer32,
				fnReturnLaserCurrent
					INTEGER,
				fnReturnLaserTemp
					INTEGER,
				fnReturnLaserControl
					INTEGER,
				fnReturnLaserType
					DisplayString,
				fnReturnLaserWavelength
					DisplayString,
				fnReturnLaserOpticalPower
					INTEGER,
				fnReturnLaserRFActive
					Integer32
			 }

--         1.3.6.1.4.1.1.1.10.3.1.1
-- 1.3.6.1.4.1.17409.1.10.3.1.1
-- 1.3.6.1.4.1.17409.1.10.3.1.1
-- 1.3.6.1.4.1.17409.1.10.3.1.1
-- 1.3.6.1.4.1.17409.1.10.3.1.1
-- 1.3.6.1.4.1.17409.1.10.3.1.1
-- 1.3.6.1.4.1.17409.1.10.3.1.1
-- 1.3.6.1.4.1.17409.1.10.3.1.1
		-- 1.3.6.1.4.1.17409.1.10.3.1.1
		fnReturnLaserIndex OBJECT-TYPE
			SYNTAX Integer32
			MAX-ACCESS read-only
			STATUS current
			DESCRIPTION
				"上行光发送机索引号，可以是上行光发送机设备的序号或是插槽编号。"
			::= { fnReturnLaserEntry 1 }

		
--         1.3.6.1.4.1.1.1.10.3.1.2
-- 1.3.6.1.4.1.17409.1.10.3.1.2
-- 1.3.6.1.4.1.17409.1.10.3.1.2
-- 1.3.6.1.4.1.17409.1.10.3.1.2
-- 1.3.6.1.4.1.17409.1.10.3.1.2
-- 1.3.6.1.4.1.17409.1.10.3.1.2
-- 1.3.6.1.4.1.17409.1.10.3.1.2
-- 1.3.6.1.4.1.17409.1.10.3.1.2
		-- 1.3.6.1.4.1.17409.1.10.3.1.2
		fnReturnLaserCurrent OBJECT-TYPE
			SYNTAX INTEGER (0..65535)
			MAX-ACCESS read-only
			STATUS optional
			DESCRIPTION
				"上行光发送机偏置电流，单位为mA。此对象要求在属性MIB中登记一个条目。"
			::= { fnReturnLaserEntry 2 }

		
--         1.3.6.1.4.1.1.1.10.3.1.3
-- 1.3.6.1.4.1.17409.1.10.3.1.3
-- 1.3.6.1.4.1.17409.1.10.3.1.3
-- 1.3.6.1.4.1.17409.1.10.3.1.3
-- 1.3.6.1.4.1.17409.1.10.3.1.3
-- 1.3.6.1.4.1.17409.1.10.3.1.3
-- 1.3.6.1.4.1.17409.1.10.3.1.3
-- 1.3.6.1.4.1.17409.1.10.3.1.3
		-- 1.3.6.1.4.1.17409.1.10.3.1.3
		fnReturnLaserTemp OBJECT-TYPE
			SYNTAX INTEGER (-32768..32767)
			MAX-ACCESS read-only
			STATUS optional
			DESCRIPTION
				"上行激光器温度，单位为0C。此对象要求在属性MIB中登记一个条目。"
			::= { fnReturnLaserEntry 3 }

		
--         1.3.6.1.4.1.1.1.10.3.1.4
-- 1.3.6.1.4.1.17409.1.10.3.1.4
-- 1.3.6.1.4.1.17409.1.10.3.1.4
-- 1.3.6.1.4.1.17409.1.10.3.1.4
-- 1.3.6.1.4.1.17409.1.10.3.1.4
-- 1.3.6.1.4.1.17409.1.10.3.1.4
-- 1.3.6.1.4.1.17409.1.10.3.1.4
-- 1.3.6.1.4.1.17409.1.10.3.1.4
		-- 1.3.6.1.4.1.17409.1.10.3.1.4
		fnReturnLaserControl OBJECT-TYPE
			SYNTAX INTEGER
				{
				off(1),
				on(2)
				}
			MAX-ACCESS read-write
			STATUS optional
			DESCRIPTION
				"上行光发送机控制使能"
			::= { fnReturnLaserEntry 4 }

		
--         1.3.6.1.4.1.1.1.10.3.1.5
-- 1.3.6.1.4.1.17409.1.10.3.1.5
-- 1.3.6.1.4.1.17409.1.10.3.1.5
-- 1.3.6.1.4.1.17409.1.10.3.1.5
-- 1.3.6.1.4.1.17409.1.10.3.1.5
-- 1.3.6.1.4.1.17409.1.10.3.1.5
-- 1.3.6.1.4.1.17409.1.10.3.1.5
-- 1.3.6.1.4.1.17409.1.10.3.1.5
		-- 1.3.6.1.4.1.17409.1.10.3.1.5
		fnReturnLaserType OBJECT-TYPE
			SYNTAX DisplayString
			MAX-ACCESS read-only
			STATUS optional
			DESCRIPTION
				"上行光发送机类型，有效值为：unisolated FP, isolated FP, uncooled DFB, cooled DFB,ITU等。"
			::= { fnReturnLaserEntry 5 }

		
--         1.3.6.1.4.1.1.1.10.3.1.6
-- 1.3.6.1.4.1.17409.1.10.3.1.6
-- 1.3.6.1.4.1.17409.1.10.3.1.6
-- 1.3.6.1.4.1.17409.1.10.3.1.6
-- 1.3.6.1.4.1.17409.1.10.3.1.6
-- 1.3.6.1.4.1.17409.1.10.3.1.6
-- 1.3.6.1.4.1.17409.1.10.3.1.6
-- 1.3.6.1.4.1.17409.1.10.3.1.6
		-- 1.3.6.1.4.1.17409.1.10.3.1.6
		fnReturnLaserWavelength OBJECT-TYPE
			SYNTAX DisplayString
			MAX-ACCESS read-only
			STATUS optional
			DESCRIPTION
				"上行光发送机的波长。"
			::= { fnReturnLaserEntry 6 }

		
--         1.3.6.1.4.1.1.1.10.3.1.7
-- 1.3.6.1.4.1.17409.1.10.3.1.7
-- 1.3.6.1.4.1.17409.1.10.3.1.7
-- 1.3.6.1.4.1.17409.1.10.3.1.7
-- 1.3.6.1.4.1.17409.1.10.3.1.7
-- 1.3.6.1.4.1.17409.1.10.3.1.7
-- 1.3.6.1.4.1.17409.1.10.3.1.7
-- 1.3.6.1.4.1.17409.1.10.3.1.7
		-- 1.3.6.1.4.1.17409.1.10.3.1.7
		fnReturnLaserOpticalPower OBJECT-TYPE
			SYNTAX INTEGER (0..65535)
			MAX-ACCESS read-only
			STATUS current
			DESCRIPTION
				"上行光发送机光功率，单位为0.1毫瓦。此对象要求在属性MIB中登记一个条目。"
			::= { fnReturnLaserEntry 7 }

		
--         1.3.6.1.4.1.1.1.10.3.1.8
-- 1.3.6.1.4.1.17409.1.10.3.1.8
-- 1.3.6.1.4.1.17409.1.10.3.1.8
-- 1.3.6.1.4.1.17409.1.10.3.1.8
-- 1.3.6.1.4.1.17409.1.10.3.1.8
-- 1.3.6.1.4.1.17409.1.10.3.1.8
-- 1.3.6.1.4.1.17409.1.10.3.1.8
-- 1.3.6.1.4.1.17409.1.10.3.1.8
		-- 1.3.6.1.4.1.17409.1.10.3.1.8
		fnReturnLaserRFActive OBJECT-TYPE
			SYNTAX Integer32
			MAX-ACCESS read-only
			STATUS current
			DESCRIPTION
				"返回与上行光发送机关联的RF工作通道索引。"
			::= { fnReturnLaserEntry 8 }

		
--          ********************
-- * 下行光接收机
-- ********************
-- 1.3.6.1.4.1.1.1.10.4
-- 1.3.6.1.4.1.17409.1.10.4
-- 1.3.6.1.4.1.17409.1.10.4
-- 1.3.6.1.4.1.17409.1.10.4
-- 1.3.6.1.4.1.17409.1.10.4
-- 1.3.6.1.4.1.17409.1.10.4
-- 1.3.6.1.4.1.17409.1.10.4
-- 1.3.6.1.4.1.17409.1.10.4
		-- 1.3.6.1.4.1.17409.1.10.4
		fnNumberOpticalReceiver OBJECT-TYPE
			SYNTAX INTEGER (0..16)
			MAX-ACCESS read-only
			STATUS current
			DESCRIPTION
				"下行光接收机表中的条目数，'0'表示设备无此功能。"
			::= { fnIdent 4 }

		
--         1.3.6.1.4.1.1.1.10.5
-- 1.3.6.1.4.1.17409.1.10.5
-- 1.3.6.1.4.1.17409.1.10.5
-- 1.3.6.1.4.1.17409.1.10.5
-- 1.3.6.1.4.1.17409.1.10.5
-- 1.3.6.1.4.1.17409.1.10.5
-- 1.3.6.1.4.1.17409.1.10.5
-- 1.3.6.1.4.1.17409.1.10.5
		-- 1.3.6.1.4.1.17409.1.10.5
		fnOpticalReceiverTable OBJECT-TYPE
			SYNTAX SEQUENCE OF FnOpticalReceiverEntry
			MAX-ACCESS not-accessible
			STATUS current
			DESCRIPTION
				"下行光接收机表。"
			::= { fnIdent 5 }

		
--         1.3.6.1.4.1.1.1.10.5.1
-- 1.3.6.1.4.1.17409.1.10.5.1
-- 1.3.6.1.4.1.17409.1.10.5.1
-- 1.3.6.1.4.1.17409.1.10.5.1
-- 1.3.6.1.4.1.17409.1.10.5.1
-- 1.3.6.1.4.1.17409.1.10.5.1
-- 1.3.6.1.4.1.17409.1.10.5.1
-- 1.3.6.1.4.1.17409.1.10.5.1
		-- 1.3.6.1.4.1.17409.1.10.5.1
		fnOpticalReceiverEntry OBJECT-TYPE
			SYNTAX FnOpticalReceiverEntry
			MAX-ACCESS not-accessible
			STATUS current
			DESCRIPTION
				"下行光接收机表目。"
			INDEX { fnOpticalReceiverIndex }
			::= { fnOpticalReceiverTable 1 }

		
		FnOpticalReceiverEntry ::=
			SEQUENCE { 
				fnOpticalReceiverIndex
					Integer32,
				fnOpticalReceiverPower
					INTEGER,
				fnOpticalReceiverState
					INTEGER,
				fnOpticalReceiverRFActive
					Integer32
			 }

--         1.3.6.1.4.1.1.1.10.5.1.1
-- 1.3.6.1.4.1.17409.1.10.5.1.1
-- 1.3.6.1.4.1.17409.1.10.5.1.1
-- 1.3.6.1.4.1.17409.1.10.5.1.1
-- 1.3.6.1.4.1.17409.1.10.5.1.1
-- 1.3.6.1.4.1.17409.1.10.5.1.1
-- 1.3.6.1.4.1.17409.1.10.5.1.1
-- 1.3.6.1.4.1.17409.1.10.5.1.1
		-- 1.3.6.1.4.1.17409.1.10.5.1.1
		fnOpticalReceiverIndex OBJECT-TYPE
			SYNTAX Integer32
			MAX-ACCESS read-only
			STATUS current
			DESCRIPTION
				"下行光接收机索引号，可以是下行光接收机设备的序号或者是插槽编号。"
			::= { fnOpticalReceiverEntry 1 }

		
--         1.3.6.1.4.1.1.1.10.5.1.2
-- 1.3.6.1.4.1.17409.1.10.5.1.2
-- 1.3.6.1.4.1.17409.1.10.5.1.2
-- 1.3.6.1.4.1.17409.1.10.5.1.2
-- 1.3.6.1.4.1.17409.1.10.5.1.2
-- 1.3.6.1.4.1.17409.1.10.5.1.2
-- 1.3.6.1.4.1.17409.1.10.5.1.2
-- 1.3.6.1.4.1.17409.1.10.5.1.2
		-- 1.3.6.1.4.1.17409.1.10.5.1.2
		fnOpticalReceiverPower OBJECT-TYPE
			SYNTAX INTEGER (0..65535)
			MAX-ACCESS read-only
			STATUS current
			DESCRIPTION
				"下行光接收机的接收光功率，单位为0.1mW，此对象要求在属性MIB中登记一个条目。"
			::= { fnOpticalReceiverEntry 2 }

		
--         1.3.6.1.4.1.1.1.10.5.1.3
-- 1.3.6.1.4.1.17409.1.10.5.1.3
-- 1.3.6.1.4.1.17409.1.10.5.1.3
-- 1.3.6.1.4.1.17409.1.10.5.1.3
-- 1.3.6.1.4.1.17409.1.10.5.1.3
-- 1.3.6.1.4.1.17409.1.10.5.1.3
-- 1.3.6.1.4.1.17409.1.10.5.1.3
-- 1.3.6.1.4.1.17409.1.10.5.1.3
		-- 1.3.6.1.4.1.17409.1.10.5.1.3
		fnOpticalReceiverState OBJECT-TYPE
			SYNTAX INTEGER
				{
				off(1),
				on(2)
				}
			MAX-ACCESS read-only
			STATUS optional
			DESCRIPTION
				"下行光接收机的工作状态。"
			::= { fnOpticalReceiverEntry 3 }

		
--         1.3.6.1.4.1.1.1.10.5.1.4
-- 1.3.6.1.4.1.17409.1.10.5.1.4
-- 1.3.6.1.4.1.17409.1.10.5.1.4
-- 1.3.6.1.4.1.17409.1.10.5.1.4
-- 1.3.6.1.4.1.17409.1.10.5.1.4
-- 1.3.6.1.4.1.17409.1.10.5.1.4
-- 1.3.6.1.4.1.17409.1.10.5.1.4
-- 1.3.6.1.4.1.17409.1.10.5.1.4
		-- 1.3.6.1.4.1.17409.1.10.5.1.4
		fnOpticalReceiverRFActive OBJECT-TYPE
			SYNTAX Integer32
			MAX-ACCESS read-only
			STATUS current
			DESCRIPTION
				"返回与下行光接收机关联的RF工作通道索引。"
			::= { fnOpticalReceiverEntry 4 }

		
--          ********
-- * EDFA
-- ********
-- 1.3.6.1.4.1.1.1.10.6
-- 1.3.6.1.4.1.17409.1.10.6
-- 1.3.6.1.4.1.17409.1.10.6
-- 1.3.6.1.4.1.17409.1.10.6
-- 1.3.6.1.4.1.17409.1.10.6
-- 1.3.6.1.4.1.17409.1.10.6
-- 1.3.6.1.4.1.17409.1.10.6
-- 1.3.6.1.4.1.17409.1.10.6
		-- 1.3.6.1.4.1.17409.1.10.6
		fnOpticalAmpPresent OBJECT-TYPE
			SYNTAX INTEGER
				{
				no(1),
				yes(2)
				}
			MAX-ACCESS read-only
			STATUS current
			DESCRIPTION
				"表示是否存在光放大器MIB。"
			::= { fnIdent 6 }

		
--          *********************
-- * 下行RF工作通道
-- *********************
-- 1.3.6.1.4.1.1.1.10.7
-- 1.3.6.1.4.1.17409.1.10.7
-- 1.3.6.1.4.1.17409.1.10.7
-- 1.3.6.1.4.1.17409.1.10.7
-- 1.3.6.1.4.1.17409.1.10.7
-- 1.3.6.1.4.1.17409.1.10.7
-- 1.3.6.1.4.1.17409.1.10.7
-- 1.3.6.1.4.1.17409.1.10.7
		-- 1.3.6.1.4.1.17409.1.10.7
		fnNumberRFActives OBJECT-TYPE
			SYNTAX INTEGER (1..16)
			MAX-ACCESS read-only
			STATUS current
			DESCRIPTION
				"此光节点中下行RF工作通道数目。
				每个光节点至少应有一个RF工作通道。
				在fnRFPortTable表中，需要将光节点上行光发送机RF工作通道（fnReturnLaserRFActive）和光节点下行光接收机RF工作通道（fnOpticalReceiverRFActive）对象映射到同一RF工作通道。
				RF工作通道号的用处是在下行光接收机和RF分配端口之间建立对应关系。
				例子（无意涵盖全部可能的状况）:
				(具有冗余光接收机、单片射频放大的光节点)
				接收机  RF工作通道   RF端口数      上行光发送机RF工作通道   下行光接收机RF工作通道     光节点RF分配端口RF工作通道
				a       1            1～4               1                          1                              1
				b       1            1～4               1                          1                              1
				(具有单个光接收机、单片射频放大的小型光节点)
				接收机  RF工作通道   RF端口数      上行光发送机RF工作通道   下行光接收机RF工作通道     光节点RF分配端口RF工作通道
				a       1            1～3               1                          1                              1
				(具有两个射频放大部分的大型光节点)
				接收机  RF工作通道   RF端口数      上行光发送机RF工作通道   下行光接收机RF工作通道     光节点RF分配端口RF工作通道
				a       1            1～4               1                          1                              1
				b       2            5～8               2                          2                              2
				(每个端口具有独立放大，自下行光接收机到RF输出口由内部电缆连接的大型光节点)
				接收机  RF工作通道   RF端口数      上行光发送机RF工作通道   下行光接收机RF工作通道     光节点RF分配端口RF工作通道
				a       1            1～4               1                          1                              1
				b       2            5～8               2                          2                              2
				这样，无论光节点的信号通道多么复杂，都可以用RF工作通道描述。"
			::= { fnIdent 7 }

		
--         1.3.6.1.4.1.1.1.10.8
-- 1.3.6.1.4.1.17409.1.10.8
-- 1.3.6.1.4.1.17409.1.10.8
-- 1.3.6.1.4.1.17409.1.10.8
-- 1.3.6.1.4.1.17409.1.10.8
-- 1.3.6.1.4.1.17409.1.10.8
-- 1.3.6.1.4.1.17409.1.10.8
-- 1.3.6.1.4.1.17409.1.10.8
		-- 1.3.6.1.4.1.17409.1.10.8
		fnRFActiveTable OBJECT-TYPE
			SYNTAX SEQUENCE OF FnRFActiveEntry
			MAX-ACCESS not-accessible
			STATUS current
			DESCRIPTION
				"RF工作通道表。"
			::= { fnIdent 8 }

		
--         1.3.6.1.4.1.1.1.10.8.1
-- 1.3.6.1.4.1.17409.1.10.8.1
-- 1.3.6.1.4.1.17409.1.10.8.1
-- 1.3.6.1.4.1.17409.1.10.8.1
-- 1.3.6.1.4.1.17409.1.10.8.1
-- 1.3.6.1.4.1.17409.1.10.8.1
-- 1.3.6.1.4.1.17409.1.10.8.1
-- 1.3.6.1.4.1.17409.1.10.8.1
		-- 1.3.6.1.4.1.17409.1.10.8.1
		fnRFActiveEntry OBJECT-TYPE
			SYNTAX FnRFActiveEntry
			MAX-ACCESS not-accessible
			STATUS current
			DESCRIPTION
				"RF工作通道表目。"
			INDEX { fnRFActiveIndex }
			::= { fnRFActiveTable 1 }

		
		FnRFActiveEntry ::=
			SEQUENCE { 
				fnRFActiveIndex
					Integer32,
				fnRFActiveControlType
					INTEGER,
				fnRFActiveOutputLevel
					INTEGER,
				fnRFActiveCurrent
					INTEGER,
				fnRFActiveControlLevel
					Integer32
			 }

--         1.3.6.1.4.1.1.1.10.8.1.1
-- 1.3.6.1.4.1.17409.1.10.8.1.1
-- 1.3.6.1.4.1.17409.1.10.8.1.1
-- 1.3.6.1.4.1.17409.1.10.8.1.1
-- 1.3.6.1.4.1.17409.1.10.8.1.1
-- 1.3.6.1.4.1.17409.1.10.8.1.1
-- 1.3.6.1.4.1.17409.1.10.8.1.1
-- 1.3.6.1.4.1.17409.1.10.8.1.1
		-- 1.3.6.1.4.1.17409.1.10.8.1.1
		fnRFActiveIndex OBJECT-TYPE
			SYNTAX Integer32
			MAX-ACCESS read-only
			STATUS current
			DESCRIPTION
				"RF工作通道索引。"
			::= { fnRFActiveEntry 1 }

		
--         1.3.6.1.4.1.1.1.10.8.1.2
-- 1.3.6.1.4.1.17409.1.10.8.1.2
-- 1.3.6.1.4.1.17409.1.10.8.1.2
-- 1.3.6.1.4.1.17409.1.10.8.1.2
-- 1.3.6.1.4.1.17409.1.10.8.1.2
-- 1.3.6.1.4.1.17409.1.10.8.1.2
-- 1.3.6.1.4.1.17409.1.10.8.1.2
-- 1.3.6.1.4.1.17409.1.10.8.1.2
		-- 1.3.6.1.4.1.17409.1.10.8.1.2
		fnRFActiveControlType OBJECT-TYPE
			SYNTAX INTEGER
				{
				alc(1),
				asc(2),
				agc(3),
				none(4)
				}
			MAX-ACCESS read-only
			STATUS optional
			DESCRIPTION
				"RF工作通道控制类型：alc（自动电平控制）,asc（自动斜率控制）,agc（自动增益控制），无固定类型。"
			::= { fnRFActiveEntry 2 }

		
--         1.3.6.1.4.1.1.1.10.8.1.3
-- 1.3.6.1.4.1.17409.1.10.8.1.3
-- 1.3.6.1.4.1.17409.1.10.8.1.3
-- 1.3.6.1.4.1.17409.1.10.8.1.3
-- 1.3.6.1.4.1.17409.1.10.8.1.3
-- 1.3.6.1.4.1.17409.1.10.8.1.3
-- 1.3.6.1.4.1.17409.1.10.8.1.3
-- 1.3.6.1.4.1.17409.1.10.8.1.3
		-- 1.3.6.1.4.1.17409.1.10.8.1.3
		fnRFActiveOutputLevel OBJECT-TYPE
			SYNTAX INTEGER (0..127)
			MAX-ACCESS read-only
			STATUS optional
			DESCRIPTION
				"RF导频输出电平，单位为dBuV。
				此对象要求在属性MIB中登记一个条目。"
			::= { fnRFActiveEntry 3 }

		
--         1.3.6.1.4.1.1.1.10.8.1.4
-- 1.3.6.1.4.1.17409.1.10.8.1.4
-- 1.3.6.1.4.1.17409.1.10.8.1.4
-- 1.3.6.1.4.1.17409.1.10.8.1.4
-- 1.3.6.1.4.1.17409.1.10.8.1.4
-- 1.3.6.1.4.1.17409.1.10.8.1.4
-- 1.3.6.1.4.1.17409.1.10.8.1.4
-- 1.3.6.1.4.1.17409.1.10.8.1.4
		-- 1.3.6.1.4.1.17409.1.10.8.1.4
		fnRFActiveCurrent OBJECT-TYPE
			SYNTAX INTEGER (0..65535)
			MAX-ACCESS read-only
			STATUS optional
			DESCRIPTION
				"RF工作通道电流，单位为mA。
				此对象要求在属性MIB中登记一个条目。"
			::= { fnRFActiveEntry 4 }

		
--         1.3.6.1.4.1.1.1.10.8.1.5
-- 1.3.6.1.4.1.17409.1.10.8.1.5
-- 1.3.6.1.4.1.17409.1.10.8.1.5
-- 1.3.6.1.4.1.17409.1.10.8.1.5
-- 1.3.6.1.4.1.17409.1.10.8.1.5
-- 1.3.6.1.4.1.17409.1.10.8.1.5
-- 1.3.6.1.4.1.17409.1.10.8.1.5
-- 1.3.6.1.4.1.17409.1.10.8.1.5
		-- 1.3.6.1.4.1.17409.1.10.8.1.5
		fnRFActiveControlLevel OBJECT-TYPE
			SYNTAX Integer32
			MAX-ACCESS read-only
			STATUS optional
			DESCRIPTION
				"该RF工作通道控制类型所指示的控制电平，单位为0.1VDC。
				此对象要求在属性MIB中登记一个条目。"
			::= { fnRFActiveEntry 5 }

		
--          ***********
-- * RF 端口
-- ***********
-- 1.3.6.1.4.1.1.1.10.9
-- 1.3.6.1.4.1.17409.1.10.9
-- 1.3.6.1.4.1.17409.1.10.9
-- 1.3.6.1.4.1.17409.1.10.9
-- 1.3.6.1.4.1.17409.1.10.9
-- 1.3.6.1.4.1.17409.1.10.9
-- 1.3.6.1.4.1.17409.1.10.9
-- 1.3.6.1.4.1.17409.1.10.9
		-- 1.3.6.1.4.1.17409.1.10.9
		fnNumberRFPort OBJECT-TYPE
			SYNTAX INTEGER (0..16)
			MAX-ACCESS read-only
			STATUS current
			DESCRIPTION
				"RF端口数目，0表示无此功能。"
			::= { fnIdent 9 }

		
--         1.3.6.1.4.1.1.1.10.10
-- 1.3.6.1.4.1.17409.1.10.10
-- 1.3.6.1.4.1.17409.1.10.10
-- 1.3.6.1.4.1.17409.1.10.10
-- 1.3.6.1.4.1.17409.1.10.10
-- 1.3.6.1.4.1.17409.1.10.10
-- 1.3.6.1.4.1.17409.1.10.10
-- 1.3.6.1.4.1.17409.1.10.10
		-- 1.3.6.1.4.1.17409.1.10.10
		fnPortMasterAttenuationControl OBJECT-TYPE
			SYNTAX INTEGER
				{
				none(1),
				low(2),
				high(3)
				}
			MAX-ACCESS read-write
			STATUS optional
			DESCRIPTION
				"报告和控制适用于所有端口的上行通道衰减开关的状态。
				none(1): 无衰减；
				low(2): 典型的低衰减值；该衰减值可能并不适用于所用端口；
				high(3): 典型的高衰减值；该衰减值可能并不适用于所用端口。
				此对象的访问不影响fnRFPortReverseAttenuationControl对象的值"
			::= { fnIdent 10 }

		
--         1.3.6.1.4.1.1.1.10.11
-- 1.3.6.1.4.1.17409.1.10.11
-- 1.3.6.1.4.1.17409.1.10.11
-- 1.3.6.1.4.1.17409.1.10.11
-- 1.3.6.1.4.1.17409.1.10.11
-- 1.3.6.1.4.1.17409.1.10.11
-- 1.3.6.1.4.1.17409.1.10.11
-- 1.3.6.1.4.1.17409.1.10.11
		-- 1.3.6.1.4.1.17409.1.10.11
		fnRFPortTable OBJECT-TYPE
			SYNTAX SEQUENCE OF FnRFPortEntry
			MAX-ACCESS not-accessible
			STATUS current
			DESCRIPTION
				"RF端口信息表。"
			::= { fnIdent 11 }

		
--         1.3.6.1.4.1.1.1.10.11.1
-- 1.3.6.1.4.1.17409.1.10.11.1
-- 1.3.6.1.4.1.17409.1.10.11.1
-- 1.3.6.1.4.1.17409.1.10.11.1
-- 1.3.6.1.4.1.17409.1.10.11.1
-- 1.3.6.1.4.1.17409.1.10.11.1
-- 1.3.6.1.4.1.17409.1.10.11.1
-- 1.3.6.1.4.1.17409.1.10.11.1
		-- 1.3.6.1.4.1.17409.1.10.11.1
		fnRFPortEntry OBJECT-TYPE
			SYNTAX FnRFPortEntry
			MAX-ACCESS not-accessible
			STATUS current
			DESCRIPTION
				"每个RF端口信息表目。"
			INDEX { fnRFPortIndex }
			::= { fnRFPortTable 1 }

		
		FnRFPortEntry ::=
			SEQUENCE { 
				fnRFPortIndex
					Integer32,
				fnRFPortControlType
					INTEGER,
				fnRFPortControlLevel
					Integer32,
				fnRFPortOutputRFLevel
					INTEGER,
				fnRFPortRFActive
					Integer32,
				fnRFPortName
					DisplayString,
				fnRFPortReverseAttenuationControl
					INTEGER,
				fnRFPortPowerFeedStatus
					INTEGER
			 }

--         1.3.6.1.4.1.1.1.10.11.1.1
-- 1.3.6.1.4.1.17409.1.10.11.1.1
-- 1.3.6.1.4.1.17409.1.10.11.1.1
-- 1.3.6.1.4.1.17409.1.10.11.1.1
-- 1.3.6.1.4.1.17409.1.10.11.1.1
-- 1.3.6.1.4.1.17409.1.10.11.1.1
-- 1.3.6.1.4.1.17409.1.10.11.1.1
-- 1.3.6.1.4.1.17409.1.10.11.1.1
		-- 1.3.6.1.4.1.17409.1.10.11.1.1
		fnRFPortIndex OBJECT-TYPE
			SYNTAX Integer32
			MAX-ACCESS read-only
			STATUS current
			DESCRIPTION
				"RF端口索引，索引编号可根据实际应用情况确定，可以表示第几个端口，也可以是端口的编号。"
			::= { fnRFPortEntry 1 }

		
--         1.3.6.1.4.1.1.1.10.11.1.2
-- 1.3.6.1.4.1.17409.1.10.11.1.2
-- 1.3.6.1.4.1.17409.1.10.11.1.2
-- 1.3.6.1.4.1.17409.1.10.11.1.2
-- 1.3.6.1.4.1.17409.1.10.11.1.2
-- 1.3.6.1.4.1.17409.1.10.11.1.2
-- 1.3.6.1.4.1.17409.1.10.11.1.2
-- 1.3.6.1.4.1.17409.1.10.11.1.2
		-- 1.3.6.1.4.1.17409.1.10.11.1.2
		fnRFPortControlType OBJECT-TYPE
			SYNTAX INTEGER
				{
				alc(1),
				asc(2),
				agc(3),
				none(4)
				}
			MAX-ACCESS read-only
			STATUS optional
			DESCRIPTION
				"控制类型：alc（自动电平控制）,asc（自动斜率控制）,agc（自动增益控制），无固定类型。"
			::= { fnRFPortEntry 2 }

		
--         1.3.6.1.4.1.1.1.10.11.1.3
-- 1.3.6.1.4.1.17409.1.10.11.1.3
-- 1.3.6.1.4.1.17409.1.10.11.1.3
-- 1.3.6.1.4.1.17409.1.10.11.1.3
-- 1.3.6.1.4.1.17409.1.10.11.1.3
-- 1.3.6.1.4.1.17409.1.10.11.1.3
-- 1.3.6.1.4.1.17409.1.10.11.1.3
-- 1.3.6.1.4.1.17409.1.10.11.1.3
		-- 1.3.6.1.4.1.17409.1.10.11.1.3
		fnRFPortControlLevel OBJECT-TYPE
			SYNTAX Integer32
			MAX-ACCESS read-only
			STATUS optional
			DESCRIPTION
				"该RF端口控制类型所指示的控制电平，单位为0.1VDC。
				此对象要求在属性MIB中登记一个条目。"
			::= { fnRFPortEntry 3 }

		
--         1.3.6.1.4.1.1.1.10.11.1.4
-- 1.3.6.1.4.1.17409.1.10.11.1.4
-- 1.3.6.1.4.1.17409.1.10.11.1.4
-- 1.3.6.1.4.1.17409.1.10.11.1.4
-- 1.3.6.1.4.1.17409.1.10.11.1.4
-- 1.3.6.1.4.1.17409.1.10.11.1.4
-- 1.3.6.1.4.1.17409.1.10.11.1.4
-- 1.3.6.1.4.1.17409.1.10.11.1.4
		-- 1.3.6.1.4.1.17409.1.10.11.1.4
		fnRFPortOutputRFLevel OBJECT-TYPE
			SYNTAX INTEGER (0..127)
			MAX-ACCESS read-only
			STATUS optional
			DESCRIPTION
				"放大器RF端口的导频输出电平，单位为dBuV。
				此对象要求在属性MIB中登记一个条目。"
			::= { fnRFPortEntry 4 }

		
--         1.3.6.1.4.1.1.1.10.11.1.5
-- 1.3.6.1.4.1.17409.1.10.11.1.5
-- 1.3.6.1.4.1.17409.1.10.11.1.5
-- 1.3.6.1.4.1.17409.1.10.11.1.5
-- 1.3.6.1.4.1.17409.1.10.11.1.5
-- 1.3.6.1.4.1.17409.1.10.11.1.5
-- 1.3.6.1.4.1.17409.1.10.11.1.5
-- 1.3.6.1.4.1.17409.1.10.11.1.5
		-- 1.3.6.1.4.1.17409.1.10.11.1.5
		fnRFPortRFActive OBJECT-TYPE
			SYNTAX Integer32
			MAX-ACCESS read-only
			STATUS current
			DESCRIPTION
				"与此RF端口关联的RF工作通道索引。"
			::= { fnRFPortEntry 5 }

		
--         1.3.6.1.4.1.1.1.10.11.1.6
-- 1.3.6.1.4.1.17409.1.10.11.1.6
-- 1.3.6.1.4.1.17409.1.10.11.1.6
-- 1.3.6.1.4.1.17409.1.10.11.1.6
-- 1.3.6.1.4.1.17409.1.10.11.1.6
-- 1.3.6.1.4.1.17409.1.10.11.1.6
-- 1.3.6.1.4.1.17409.1.10.11.1.6
-- 1.3.6.1.4.1.17409.1.10.11.1.6
		-- 1.3.6.1.4.1.17409.1.10.11.1.6
		fnRFPortName OBJECT-TYPE
			SYNTAX DisplayString
			MAX-ACCESS read-only
			STATUS current
			DESCRIPTION
				"端口的物理名称，例如端口1和端口2。
				当此表中的对象产生告警陷阱消息时，此名称将被填入hfcAlarmTrap中的alarmText对象里。"
			::= { fnRFPortEntry 6 }

		
--         1.3.6.1.4.1.1.1.10.11.1.7
-- 1.3.6.1.4.1.17409.1.10.11.1.7
-- 1.3.6.1.4.1.17409.1.10.11.1.7
-- 1.3.6.1.4.1.17409.1.10.11.1.7
-- 1.3.6.1.4.1.17409.1.10.11.1.7
-- 1.3.6.1.4.1.17409.1.10.11.1.7
-- 1.3.6.1.4.1.17409.1.10.11.1.7
-- 1.3.6.1.4.1.17409.1.10.11.1.7
		-- 1.3.6.1.4.1.17409.1.10.11.1.7
		fnRFPortReverseAttenuationControl OBJECT-TYPE
			SYNTAX INTEGER
				{
				none(1),
				low(2),
				high(3)
				}
			MAX-ACCESS read-write
			STATUS optional
			DESCRIPTION
				"报告和控制该端口的上行通道衰减开关的状态。
				none(1): 无衰减；
				low(2): 上行通道典型的低衰减值，该衰减值可能并不适用于所有开关。
				high(3): 上行通道典型的高衰减值，该衰减值可能并不适用于所用开关。"
			::= { fnRFPortEntry 7 }

		
--         1.3.6.1.4.1.1.1.10.11.1.8
-- 1.3.6.1.4.1.17409.1.10.11.1.8
-- 1.3.6.1.4.1.17409.1.10.11.1.8
-- 1.3.6.1.4.1.17409.1.10.11.1.8
-- 1.3.6.1.4.1.17409.1.10.11.1.8
-- 1.3.6.1.4.1.17409.1.10.11.1.8
-- 1.3.6.1.4.1.17409.1.10.11.1.8
-- 1.3.6.1.4.1.17409.1.10.11.1.8
		-- 1.3.6.1.4.1.17409.1.10.11.1.8
		fnRFPortPowerFeedStatus OBJECT-TYPE
			SYNTAX INTEGER
				{
				on(1),
				off(2)
				}
			MAX-ACCESS read-only
			STATUS optional
			DESCRIPTION
				"RF端口馈电状态，'1'表示有馈电，'2'表示无馈电"
			::= { fnRFPortEntry 8 }

		
--          **************
-- * AB开关
-- **************
-- 1.3.6.1.4.1.1.1.10.12
-- 1.3.6.1.4.1.17409.1.10.12
-- 1.3.6.1.4.1.17409.1.10.12
-- 1.3.6.1.4.1.17409.1.10.12
-- 1.3.6.1.4.1.17409.1.10.12
-- 1.3.6.1.4.1.17409.1.10.12
-- 1.3.6.1.4.1.17409.1.10.12
-- 1.3.6.1.4.1.17409.1.10.12
		-- 1.3.6.1.4.1.17409.1.10.12
		fnNumberABSwitch OBJECT-TYPE
			SYNTAX INTEGER (0..16)
			MAX-ACCESS read-only
			STATUS current
			DESCRIPTION
				"此光节点上AB开关总数，0表示设备无此功能。"
			::= { fnIdent 12 }

		
--         1.3.6.1.4.1.1.1.10.13
-- 1.3.6.1.4.1.17409.1.10.13
-- 1.3.6.1.4.1.17409.1.10.13
-- 1.3.6.1.4.1.17409.1.10.13
-- 1.3.6.1.4.1.17409.1.10.13
-- 1.3.6.1.4.1.17409.1.10.13
-- 1.3.6.1.4.1.17409.1.10.13
-- 1.3.6.1.4.1.17409.1.10.13
		-- 1.3.6.1.4.1.17409.1.10.13
		fnABSwitchTable OBJECT-TYPE
			SYNTAX SEQUENCE OF FnABSwitchEntry
			MAX-ACCESS not-accessible
			STATUS current
			DESCRIPTION
				"该光节点内的AB开关信息表"
			::= { fnIdent 13 }

		
--         1.3.6.1.4.1.1.1.10.13.1
-- 1.3.6.1.4.1.17409.1.10.13.1
-- 1.3.6.1.4.1.17409.1.10.13.1
-- 1.3.6.1.4.1.17409.1.10.13.1
-- 1.3.6.1.4.1.17409.1.10.13.1
-- 1.3.6.1.4.1.17409.1.10.13.1
-- 1.3.6.1.4.1.17409.1.10.13.1
-- 1.3.6.1.4.1.17409.1.10.13.1
		-- 1.3.6.1.4.1.17409.1.10.13.1
		fnABSwitchEntry OBJECT-TYPE
			SYNTAX FnABSwitchEntry
			MAX-ACCESS not-accessible
			STATUS current
			DESCRIPTION
				"AB开关信息表目"
			INDEX { fnABSwitchIndex }
			::= { fnABSwitchTable 1 }

		
		FnABSwitchEntry ::=
			SEQUENCE { 
				fnABSwitchIndex
					Integer32,
				fnOpticalReceiverABSwitchState
					INTEGER,
				fnOpticalReceiverABSwitchControl
					INTEGER
			 }

--         1.3.6.1.4.1.1.1.10.13.1.1
-- 1.3.6.1.4.1.17409.1.10.13.1.1
-- 1.3.6.1.4.1.17409.1.10.13.1.1
-- 1.3.6.1.4.1.17409.1.10.13.1.1
-- 1.3.6.1.4.1.17409.1.10.13.1.1
-- 1.3.6.1.4.1.17409.1.10.13.1.1
-- 1.3.6.1.4.1.17409.1.10.13.1.1
-- 1.3.6.1.4.1.17409.1.10.13.1.1
		-- 1.3.6.1.4.1.17409.1.10.13.1.1
		fnABSwitchIndex OBJECT-TYPE
			SYNTAX Integer32
			MAX-ACCESS read-only
			STATUS current
			DESCRIPTION
				"AB开关索引"
			::= { fnABSwitchEntry 1 }

		
--         1.3.6.1.4.1.1.1.10.13.1.2
-- 1.3.6.1.4.1.17409.1.10.13.1.2
-- 1.3.6.1.4.1.17409.1.10.13.1.2
-- 1.3.6.1.4.1.17409.1.10.13.1.2
-- 1.3.6.1.4.1.17409.1.10.13.1.2
-- 1.3.6.1.4.1.17409.1.10.13.1.2
-- 1.3.6.1.4.1.17409.1.10.13.1.2
-- 1.3.6.1.4.1.17409.1.10.13.1.2
		-- 1.3.6.1.4.1.17409.1.10.13.1.2
		fnOpticalReceiverABSwitchState OBJECT-TYPE
			SYNTAX INTEGER
				{
				pathA(1),
				pathB(2)
				}
			MAX-ACCESS read-only
			STATUS current
			DESCRIPTION
				"报告AB开关的状态，此对象要求在属性MIB中登记一个条目。"
			::= { fnABSwitchEntry 2 }

		
--         1.3.6.1.4.1.1.1.10.13.1.3
-- 1.3.6.1.4.1.17409.1.10.13.1.3
-- 1.3.6.1.4.1.17409.1.10.13.1.3
-- 1.3.6.1.4.1.17409.1.10.13.1.3
-- 1.3.6.1.4.1.17409.1.10.13.1.3
-- 1.3.6.1.4.1.17409.1.10.13.1.3
-- 1.3.6.1.4.1.17409.1.10.13.1.3
-- 1.3.6.1.4.1.17409.1.10.13.1.3
		-- 1.3.6.1.4.1.17409.1.10.13.1.3
		fnOpticalReceiverABSwitchControl OBJECT-TYPE
			SYNTAX INTEGER
				{
				forcePathA(1),
				forcePathB(2),
				preferPathA(3),
				preferPathB(4)
				}
			MAX-ACCESS read-write
			STATUS current
			DESCRIPTION
				"光接收机的AB开关控制
				forcePathA －　强制AB开关切换到通道A上。禁止任何自动切换。
				forcePathB －　强制AB开关切换到通道B上。禁止任何自动切换。
				preferPathA －　允许自动切换，通道A优先。厂商可以规定在一定条件下切换到通道B。但条件不再满足时AB开关将自动切换回通道A。
				preferPathB－　允许自动切换，通道B优先。厂商可以规定在一定条件下切换到通道A。但条件不再满足时AB开关将自动切换回通道B。	
				光节点应答器不必支持所有的枚举值。如果接收到的设置指令的参数值是不支持的，则回应一个BADVALUE错误。"
			::= { fnABSwitchEntry 3 }

		
--          ***********
-- * 交流电源
-- ***********
-- 1.3.6.1.4.1.1.1.10.14
-- 1.3.6.1.4.1.17409.1.10.14
-- 1.3.6.1.4.1.17409.1.10.14
-- 1.3.6.1.4.1.17409.1.10.14
-- 1.3.6.1.4.1.17409.1.10.14
-- 1.3.6.1.4.1.17409.1.10.14
-- 1.3.6.1.4.1.17409.1.10.14
-- 1.3.6.1.4.1.17409.1.10.14
		-- 1.3.6.1.4.1.17409.1.10.14
		fnLinePowerVoltage1 OBJECT-TYPE
			SYNTAX INTEGER (0..65535)
			MAX-ACCESS read-only
			STATUS optional
			DESCRIPTION
				"线路电源电压，单位为1VAC。此对象要求在属性MIB中登记一个条目。"
			::= { fnIdent 14 }

		
--         1.3.6.1.4.1.1.1.10.15
-- 1.3.6.1.4.1.17409.1.10.15
-- 1.3.6.1.4.1.17409.1.10.15
-- 1.3.6.1.4.1.17409.1.10.15
-- 1.3.6.1.4.1.17409.1.10.15
-- 1.3.6.1.4.1.17409.1.10.15
-- 1.3.6.1.4.1.17409.1.10.15
-- 1.3.6.1.4.1.17409.1.10.15
		-- 1.3.6.1.4.1.17409.1.10.15
		fnLinePowerVoltage2 OBJECT-TYPE
			SYNTAX INTEGER (0..65535)
			MAX-ACCESS read-only
			STATUS optional
			DESCRIPTION
				"备份线路电源电压，单位为1VAC。此对象要求在属性MIB中登记一个条目。"
			::= { fnIdent 15 }

		
--         1.3.6.1.4.1.1.1.10.16
-- 1.3.6.1.4.1.17409.1.10.16
-- 1.3.6.1.4.1.17409.1.10.16
-- 1.3.6.1.4.1.17409.1.10.16
-- 1.3.6.1.4.1.17409.1.10.16
-- 1.3.6.1.4.1.17409.1.10.16
-- 1.3.6.1.4.1.17409.1.10.16
-- 1.3.6.1.4.1.17409.1.10.16
		-- 1.3.6.1.4.1.17409.1.10.16
		fnLinePowerCurrent OBJECT-TYPE
			SYNTAX INTEGER (0..65535)
			MAX-ACCESS read-only
			STATUS optional
			DESCRIPTION
				"光节点的总电流，单位为0.1A。此对象要求在属性MIB中登记一个条目。"
			::= { fnIdent 16 }

		
--          *****************
-- * 直流电源
-- *****************
-- 1.3.6.1.4.1.1.1.10.17
-- 1.3.6.1.4.1.17409.1.10.17
-- 1.3.6.1.4.1.17409.1.10.17
-- 1.3.6.1.4.1.17409.1.10.17
-- 1.3.6.1.4.1.17409.1.10.17
-- 1.3.6.1.4.1.17409.1.10.17
-- 1.3.6.1.4.1.17409.1.10.17
-- 1.3.6.1.4.1.17409.1.10.17
		-- 1.3.6.1.4.1.17409.1.10.17
		fnNumberDCPowerSupply OBJECT-TYPE
			SYNTAX INTEGER (0..16)
			MAX-ACCESS read-only
			STATUS current
			DESCRIPTION
				"内部直流电源的数目，'0'表示设备无此功能。"
			::= { fnIdent 17 }

		
--         1.3.6.1.4.1.1.1.10.18
-- 1.3.6.1.4.1.17409.1.10.18
-- 1.3.6.1.4.1.17409.1.10.18
-- 1.3.6.1.4.1.17409.1.10.18
-- 1.3.6.1.4.1.17409.1.10.18
-- 1.3.6.1.4.1.17409.1.10.18
-- 1.3.6.1.4.1.17409.1.10.18
-- 1.3.6.1.4.1.17409.1.10.18
		-- 1.3.6.1.4.1.17409.1.10.18
		fnDCPowerSupplyMode OBJECT-TYPE
			SYNTAX INTEGER
				{
				loadsharing(1),
				switchedRedundant(2)
				}
			MAX-ACCESS read-only
			STATUS optional
			DESCRIPTION
				"供电电源工作模式：负载分担或备用切换。
				如果设备仅有一个直流电源供电，此对象不应被支持。"
			::= { fnIdent 18 }

		
--         1.3.6.1.4.1.1.1.10.19
-- 1.3.6.1.4.1.17409.1.10.19
-- 1.3.6.1.4.1.17409.1.10.19
-- 1.3.6.1.4.1.17409.1.10.19
-- 1.3.6.1.4.1.17409.1.10.19
-- 1.3.6.1.4.1.17409.1.10.19
-- 1.3.6.1.4.1.17409.1.10.19
-- 1.3.6.1.4.1.17409.1.10.19
		-- 1.3.6.1.4.1.17409.1.10.19
		fnDCPowerTable OBJECT-TYPE
			SYNTAX SEQUENCE OF FnDCPowerEntry
			MAX-ACCESS not-accessible
			STATUS current
			DESCRIPTION
				"直流电源信息表"
			::= { fnIdent 19 }

		
--         1.3.6.1.4.1.1.1.10.19.1
-- 1.3.6.1.4.1.17409.1.10.19.1
-- 1.3.6.1.4.1.17409.1.10.19.1
-- 1.3.6.1.4.1.17409.1.10.19.1
-- 1.3.6.1.4.1.17409.1.10.19.1
-- 1.3.6.1.4.1.17409.1.10.19.1
-- 1.3.6.1.4.1.17409.1.10.19.1
-- 1.3.6.1.4.1.17409.1.10.19.1
		-- 1.3.6.1.4.1.17409.1.10.19.1
		fnDCPowerEntry OBJECT-TYPE
			SYNTAX FnDCPowerEntry
			MAX-ACCESS not-accessible
			STATUS current
			DESCRIPTION
				"直流电源信息表目。"
			INDEX { fnDCPowerIndex }
			::= { fnDCPowerTable 1 }

		
		FnDCPowerEntry ::=
			SEQUENCE { 
				fnDCPowerIndex
					Integer32,
				fnDCPowerVoltage
					INTEGER,
				fnDCPowerCurrent
					INTEGER,
				fnDCPowerName
					DisplayString
			 }

--         1.3.6.1.4.1.1.1.10.19.1.1
-- 1.3.6.1.4.1.17409.1.10.19.1.1
-- 1.3.6.1.4.1.17409.1.10.19.1.1
-- 1.3.6.1.4.1.17409.1.10.19.1.1
-- 1.3.6.1.4.1.17409.1.10.19.1.1
-- 1.3.6.1.4.1.17409.1.10.19.1.1
-- 1.3.6.1.4.1.17409.1.10.19.1.1
-- 1.3.6.1.4.1.17409.1.10.19.1.1
		-- 1.3.6.1.4.1.17409.1.10.19.1.1
		fnDCPowerIndex OBJECT-TYPE
			SYNTAX Integer32
			MAX-ACCESS read-only
			STATUS current
			DESCRIPTION
				"直流电源索引,表fnDCPowerTable的索引。"
			::= { fnDCPowerEntry 1 }

		
--         1.3.6.1.4.1.1.1.10.19.1.2
-- 1.3.6.1.4.1.17409.1.10.19.1.2
-- 1.3.6.1.4.1.17409.1.10.19.1.2
-- 1.3.6.1.4.1.17409.1.10.19.1.2
-- 1.3.6.1.4.1.17409.1.10.19.1.2
-- 1.3.6.1.4.1.17409.1.10.19.1.2
-- 1.3.6.1.4.1.17409.1.10.19.1.2
-- 1.3.6.1.4.1.17409.1.10.19.1.2
		-- 1.3.6.1.4.1.17409.1.10.19.1.2
		fnDCPowerVoltage OBJECT-TYPE
			SYNTAX INTEGER (-32768..32767)
			MAX-ACCESS read-only
			STATUS current
			DESCRIPTION
				"电源电压，单位为0.1V。此对象要求在属性MIB中登记一个条目。"
			::= { fnDCPowerEntry 2 }

		
--         1.3.6.1.4.1.1.1.10.19.1.3
-- 1.3.6.1.4.1.17409.1.10.19.1.3
-- 1.3.6.1.4.1.17409.1.10.19.1.3
-- 1.3.6.1.4.1.17409.1.10.19.1.3
-- 1.3.6.1.4.1.17409.1.10.19.1.3
-- 1.3.6.1.4.1.17409.1.10.19.1.3
-- 1.3.6.1.4.1.17409.1.10.19.1.3
-- 1.3.6.1.4.1.17409.1.10.19.1.3
		-- 1.3.6.1.4.1.17409.1.10.19.1.3
		fnDCPowerCurrent OBJECT-TYPE
			SYNTAX INTEGER (0..65535)
			MAX-ACCESS read-only
			STATUS optional
			DESCRIPTION
				"电源电流，单位为0.1A。此对象要求在属性MIB中登记一个条目。"
			::= { fnDCPowerEntry 3 }

		
--         1.3.6.1.4.1.1.1.10.19.1.4
-- 1.3.6.1.4.1.17409.1.10.19.1.4
-- 1.3.6.1.4.1.17409.1.10.19.1.4
-- 1.3.6.1.4.1.17409.1.10.19.1.4
-- 1.3.6.1.4.1.17409.1.10.19.1.4
-- 1.3.6.1.4.1.17409.1.10.19.1.4
-- 1.3.6.1.4.1.17409.1.10.19.1.4
-- 1.3.6.1.4.1.17409.1.10.19.1.4
		-- 1.3.6.1.4.1.17409.1.10.19.1.4
		fnDCPowerName OBJECT-TYPE
			SYNTAX DisplayString
			MAX-ACCESS read-only
			STATUS current
			DESCRIPTION
				"标明直流电源名称，例如：24V直流电源。
				此字段值由用户规定，至少应标明工作电压并将多个电源相互区分开。
				当此表中的对象产生告警时，此对象名称应放进hfcAlarmEvent陷阱的alarmText对象里。"
			::= { fnDCPowerEntry 4 }

		
--              DESCRIPTION
-- "光节点(Fiber Node)MIB的分支节点标识符。"
-- "见附录L。"
-- 1.3.6.1.4.1.1.1.11
-- 1.3.6.1.4.1.17409.1.11
-- 1.3.6.1.4.1.17409.1.11
-- 1.3.6.1.4.1.17409.1.11
-- 1.3.6.1.4.1.17409.1.11
-- 1.3.6.1.4.1.17409.1.11
-- 1.3.6.1.4.1.17409.1.11
-- 1.3.6.1.4.1.17409.1.11
		-- 1.3.6.1.4.1.17409.1.11
		oaIdent OBJECT IDENTIFIER ::= { nscrtvHFCemsTree 11 }

		
--         *********************************************************************************************
-- 光放大器MIB
-- *********************************************************************************************
-- 1.3.6.1.4.1.1.1.11.1
-- 1.3.6.1.4.1.17409.1.11.1
-- 1.3.6.1.4.1.17409.1.11.1
-- 1.3.6.1.4.1.17409.1.11.1
-- 1.3.6.1.4.1.17409.1.11.1
-- 1.3.6.1.4.1.17409.1.11.1
-- 1.3.6.1.4.1.17409.1.11.1
-- 1.3.6.1.4.1.17409.1.11.1
		-- 1.3.6.1.4.1.17409.1.11.1
		oaVendorOID OBJECT-TYPE
			SYNTAX OBJECT IDENTIFIER
			MAX-ACCESS read-only
			STATUS optional
			DESCRIPTION
				"此对象提供厂商对光放大器MIB的扩充。无扩充时此对象应指向光放大器节点oaIdent。"
			::= { oaIdent 1 }

		
--         1.3.6.1.4.1.1.1.11.2
-- 1.3.6.1.4.1.17409.1.11.2
-- 1.3.6.1.4.1.17409.1.11.2
-- 1.3.6.1.4.1.17409.1.11.2
-- 1.3.6.1.4.1.17409.1.11.2
-- 1.3.6.1.4.1.17409.1.11.2
-- 1.3.6.1.4.1.17409.1.11.2
-- 1.3.6.1.4.1.17409.1.11.2
		-- 1.3.6.1.4.1.17409.1.11.2
		oaOutputOpticalPower OBJECT-TYPE
			SYNTAX INTEGER (0..65535)
			MAX-ACCESS read-only
			STATUS current
			DESCRIPTION
				"输出光功率,单位为0.1dBm,此对象要求在属性MIB中登记一个条目。"
			::= { oaIdent 2 }

		
--         1.3.6.1.4.1.1.1.11.3
-- 1.3.6.1.4.1.17409.1.11.3
-- 1.3.6.1.4.1.17409.1.11.3
-- 1.3.6.1.4.1.17409.1.11.3
-- 1.3.6.1.4.1.17409.1.11.3
-- 1.3.6.1.4.1.17409.1.11.3
-- 1.3.6.1.4.1.17409.1.11.3
-- 1.3.6.1.4.1.17409.1.11.3
		-- 1.3.6.1.4.1.17409.1.11.3
		oaInputOpticalPower OBJECT-TYPE
			SYNTAX INTEGER (-128..127)
			MAX-ACCESS read-only
			STATUS current
			DESCRIPTION
				"输入光功率,单位为0.1dBm,此对象要求在属性MIB中登记一个条目。"
			::= { oaIdent 3 }

		
--          ****************
-- * 激光泵参数
-- ****************
-- 1.3.6.1.4.1.1.1.11.4
-- 1.3.6.1.4.1.17409.1.11.4
-- 1.3.6.1.4.1.17409.1.11.4
-- 1.3.6.1.4.1.17409.1.11.4
-- 1.3.6.1.4.1.17409.1.11.4
-- 1.3.6.1.4.1.17409.1.11.4
-- 1.3.6.1.4.1.17409.1.11.4
-- 1.3.6.1.4.1.17409.1.11.4
		-- 1.3.6.1.4.1.17409.1.11.4
		oaPumpTable OBJECT-TYPE
			SYNTAX SEQUENCE OF OaPumpEntry
			MAX-ACCESS not-accessible
			STATUS current
			DESCRIPTION
				"EDFA激光泵信息表。"
			::= { oaIdent 4 }

		
--         1.3.6.1.4.1.1.1.11.4.1
-- 1.3.6.1.4.1.17409.1.11.4.1
-- 1.3.6.1.4.1.17409.1.11.4.1
-- 1.3.6.1.4.1.17409.1.11.4.1
-- 1.3.6.1.4.1.17409.1.11.4.1
-- 1.3.6.1.4.1.17409.1.11.4.1
-- 1.3.6.1.4.1.17409.1.11.4.1
-- 1.3.6.1.4.1.17409.1.11.4.1
		-- 1.3.6.1.4.1.17409.1.11.4.1
		oaPumpEntry OBJECT-TYPE
			SYNTAX OaPumpEntry
			MAX-ACCESS not-accessible
			STATUS current
			DESCRIPTION
				"每个光放大器激光泵浦的信息表目。"
			INDEX { oaPumpIndex }
			::= { oaPumpTable 1 }

		
		OaPumpEntry ::=
			SEQUENCE { 
				oaPumpIndex
					Integer32,
				oaPumpBIAS
					INTEGER,
				oaPumpTEC
					INTEGER,
				oaPumpTemp
					INTEGER
			 }

--         1.3.6.1.4.1.1.1.11.4.1.1
-- 1.3.6.1.4.1.17409.1.11.4.1.1
-- 1.3.6.1.4.1.17409.1.11.4.1.1
-- 1.3.6.1.4.1.17409.1.11.4.1.1
-- 1.3.6.1.4.1.17409.1.11.4.1.1
-- 1.3.6.1.4.1.17409.1.11.4.1.1
-- 1.3.6.1.4.1.17409.1.11.4.1.1
-- 1.3.6.1.4.1.17409.1.11.4.1.1
		-- 1.3.6.1.4.1.17409.1.11.4.1.1
		oaPumpIndex OBJECT-TYPE
			SYNTAX Integer32
			MAX-ACCESS read-only
			STATUS current
			DESCRIPTION
				"光放大器激光泵浦索引值。"
			::= { oaPumpEntry 1 }

		
--         1.3.6.1.4.1.1.1.11.4.1.2
-- 1.3.6.1.4.1.17409.1.11.4.1.2
-- 1.3.6.1.4.1.17409.1.11.4.1.2
-- 1.3.6.1.4.1.17409.1.11.4.1.2
-- 1.3.6.1.4.1.17409.1.11.4.1.2
-- 1.3.6.1.4.1.17409.1.11.4.1.2
-- 1.3.6.1.4.1.17409.1.11.4.1.2
-- 1.3.6.1.4.1.17409.1.11.4.1.2
		-- 1.3.6.1.4.1.17409.1.11.4.1.2
		oaPumpBIAS OBJECT-TYPE
			SYNTAX INTEGER (0..65535)
			MAX-ACCESS read-only
			STATUS current
			DESCRIPTION
				"激光泵浦偏置电流,单位为mA,此对象要求在属性MIB中登记一个条目。"
			::= { oaPumpEntry 2 }

		
--         1.3.6.1.4.1.1.1.11.4.1.3
-- 1.3.6.1.4.1.17409.1.11.4.1.3
-- 1.3.6.1.4.1.17409.1.11.4.1.3
-- 1.3.6.1.4.1.17409.1.11.4.1.3
-- 1.3.6.1.4.1.17409.1.11.4.1.3
-- 1.3.6.1.4.1.17409.1.11.4.1.3
-- 1.3.6.1.4.1.17409.1.11.4.1.3
-- 1.3.6.1.4.1.17409.1.11.4.1.3
		-- 1.3.6.1.4.1.17409.1.11.4.1.3
		oaPumpTEC OBJECT-TYPE
			SYNTAX INTEGER (-32768..32767)
			MAX-ACCESS read-only
			STATUS optional
			DESCRIPTION
				"激光泵致冷电流,单位为0.01A,此对象要求在属性MIB中登记一个条目。"
			::= { oaPumpEntry 3 }

		
--         1.3.6.1.4.1.1.1.11.4.1.4
-- 1.3.6.1.4.1.17409.1.11.4.1.4
-- 1.3.6.1.4.1.17409.1.11.4.1.4
-- 1.3.6.1.4.1.17409.1.11.4.1.4
-- 1.3.6.1.4.1.17409.1.11.4.1.4
-- 1.3.6.1.4.1.17409.1.11.4.1.4
-- 1.3.6.1.4.1.17409.1.11.4.1.4
-- 1.3.6.1.4.1.17409.1.11.4.1.4
		-- 1.3.6.1.4.1.17409.1.11.4.1.4
		oaPumpTemp OBJECT-TYPE
			SYNTAX INTEGER (0..32768)
			MAX-ACCESS read-only
			STATUS current
			DESCRIPTION
				"激光泵温度,单位为0.10C,此对象要求在属性MIB中登记一个条目。"
			::= { oaPumpEntry 4 }

		
--          *****************
-- * 直流电源
-- *****************
-- 1.3.6.1.4.1.1.1.11.5
-- 1.3.6.1.4.1.17409.1.11.5
-- 1.3.6.1.4.1.17409.1.11.5
-- 1.3.6.1.4.1.17409.1.11.5
-- 1.3.6.1.4.1.17409.1.11.5
-- 1.3.6.1.4.1.17409.1.11.5
-- 1.3.6.1.4.1.17409.1.11.5
-- 1.3.6.1.4.1.17409.1.11.5
		-- 1.3.6.1.4.1.17409.1.11.5
		oaNumberDCPowerSupply OBJECT-TYPE
			SYNTAX INTEGER (0..16)
			MAX-ACCESS read-only
			STATUS current
			DESCRIPTION
				"内部直流电源的数目，0表示应答器不支持此功能。"
			::= { oaIdent 5 }

		
--         1.3.6.1.4.1.1.1.11.6
-- 1.3.6.1.4.1.17409.1.11.6
-- 1.3.6.1.4.1.17409.1.11.6
-- 1.3.6.1.4.1.17409.1.11.6
-- 1.3.6.1.4.1.17409.1.11.6
-- 1.3.6.1.4.1.17409.1.11.6
-- 1.3.6.1.4.1.17409.1.11.6
-- 1.3.6.1.4.1.17409.1.11.6
		-- 1.3.6.1.4.1.17409.1.11.6
		oaDCPowerSupplyMode OBJECT-TYPE
			SYNTAX INTEGER
				{
				loadsharing(1),
				switchedRedundant(2),
				aloneSupply(3)
				}
			MAX-ACCESS read-only
			STATUS optional
			DESCRIPTION
				"供电电源工作模式：负载分担、备用切换或独立供电。"
			::= { oaIdent 6 }

		
--         1.3.6.1.4.1.1.1.11.7
-- 1.3.6.1.4.1.17409.1.11.7
-- 1.3.6.1.4.1.17409.1.11.7
-- 1.3.6.1.4.1.17409.1.11.7
-- 1.3.6.1.4.1.17409.1.11.7
-- 1.3.6.1.4.1.17409.1.11.7
-- 1.3.6.1.4.1.17409.1.11.7
-- 1.3.6.1.4.1.17409.1.11.7
		-- 1.3.6.1.4.1.17409.1.11.7
		oaDCPowerTable OBJECT-TYPE
			SYNTAX SEQUENCE OF OaDCPowerEntry
			MAX-ACCESS not-accessible
			STATUS current
			DESCRIPTION
				"直流电源信息表。"
			::= { oaIdent 7 }

		
--         1.3.6.1.4.1.1.1.11.7.1
-- 1.3.6.1.4.1.17409.1.11.7.1
-- 1.3.6.1.4.1.17409.1.11.7.1
-- 1.3.6.1.4.1.17409.1.11.7.1
-- 1.3.6.1.4.1.17409.1.11.7.1
-- 1.3.6.1.4.1.17409.1.11.7.1
-- 1.3.6.1.4.1.17409.1.11.7.1
-- 1.3.6.1.4.1.17409.1.11.7.1
		-- 1.3.6.1.4.1.17409.1.11.7.1
		oaDCPowerEntry OBJECT-TYPE
			SYNTAX OaDCPowerEntry
			MAX-ACCESS not-accessible
			STATUS current
			DESCRIPTION
				"直流电源信息表目。"
			INDEX { oaDCPowerIndex }
			::= { oaDCPowerTable 1 }

		
		OaDCPowerEntry ::=
			SEQUENCE { 
				oaDCPowerIndex
					Integer32,
				oaDCPowerVoltage
					INTEGER,
				oaDCPowerCurrent
					INTEGER,
				oaDCPowerName
					DisplayString
			 }

--         1.3.6.1.4.1.1.1.11.7.1.1
-- 1.3.6.1.4.1.17409.1.11.7.1.1
-- 1.3.6.1.4.1.17409.1.11.7.1.1
-- 1.3.6.1.4.1.17409.1.11.7.1.1
-- 1.3.6.1.4.1.17409.1.11.7.1.1
-- 1.3.6.1.4.1.17409.1.11.7.1.1
-- 1.3.6.1.4.1.17409.1.11.7.1.1
-- 1.3.6.1.4.1.17409.1.11.7.1.1
		-- 1.3.6.1.4.1.17409.1.11.7.1.1
		oaDCPowerIndex OBJECT-TYPE
			SYNTAX Integer32
			MAX-ACCESS read-only
			STATUS current
			DESCRIPTION
				"直流电源索引。"
			::= { oaDCPowerEntry 1 }

		
--         1.3.6.1.4.1.1.1.11.7.1.2
-- 1.3.6.1.4.1.17409.1.11.7.1.2
-- 1.3.6.1.4.1.17409.1.11.7.1.2
-- 1.3.6.1.4.1.17409.1.11.7.1.2
-- 1.3.6.1.4.1.17409.1.11.7.1.2
-- 1.3.6.1.4.1.17409.1.11.7.1.2
-- 1.3.6.1.4.1.17409.1.11.7.1.2
-- 1.3.6.1.4.1.17409.1.11.7.1.2
		-- 1.3.6.1.4.1.17409.1.11.7.1.2
		oaDCPowerVoltage OBJECT-TYPE
			SYNTAX INTEGER (-32768..32767)
			MAX-ACCESS read-only
			STATUS current
			DESCRIPTION
				"电源电压，单位为0.1V。此对象要求在属性MIB中登记一个条目。"
			::= { oaDCPowerEntry 2 }

		
--         1.3.6.1.4.1.1.1.11.7.1.3
-- 1.3.6.1.4.1.17409.1.11.7.1.3
-- 1.3.6.1.4.1.17409.1.11.7.1.3
-- 1.3.6.1.4.1.17409.1.11.7.1.3
-- 1.3.6.1.4.1.17409.1.11.7.1.3
-- 1.3.6.1.4.1.17409.1.11.7.1.3
-- 1.3.6.1.4.1.17409.1.11.7.1.3
-- 1.3.6.1.4.1.17409.1.11.7.1.3
		-- 1.3.6.1.4.1.17409.1.11.7.1.3
		oaDCPowerCurrent OBJECT-TYPE
			SYNTAX INTEGER (0..65535)
			MAX-ACCESS read-only
			STATUS current
			DESCRIPTION
				"电源的电流，单位为0.01A。此对象要求在属性MIB中登记一个条目。"
			::= { oaDCPowerEntry 3 }

		
--         1.3.6.1.4.1.1.1.11.7.1.4
-- 1.3.6.1.4.1.17409.1.11.7.1.4
-- 1.3.6.1.4.1.17409.1.11.7.1.4
-- 1.3.6.1.4.1.17409.1.11.7.1.4
-- 1.3.6.1.4.1.17409.1.11.7.1.4
-- 1.3.6.1.4.1.17409.1.11.7.1.4
-- 1.3.6.1.4.1.17409.1.11.7.1.4
-- 1.3.6.1.4.1.17409.1.11.7.1.4
		-- 1.3.6.1.4.1.17409.1.11.7.1.4
		oaDCPowerName OBJECT-TYPE
			SYNTAX DisplayString
			MAX-ACCESS read-only
			STATUS current
			DESCRIPTION
				"标明该电源的名称，例如：24V直流电源。
				此字段值由用户规定，至少应标明工作电压并将多个电源相互区分开。
				当此表中的对象产生告警时，此对象名称应放进hfcAlarmEvent陷阱的alarmText对象里。"
			::= { oaDCPowerEntry 4 }

		
--              DESCRIPTION
-- "光放大器(Optical Amplifier)MIB的分支节点标识符。"
-- "见附录M。"
-- 1.3.6.1.4.1.1.1.12
-- 1.3.6.1.4.1.17409.1.12
-- 1.3.6.1.4.1.17409.1.12
-- 1.3.6.1.4.1.17409.1.12
-- 1.3.6.1.4.1.17409.1.12
-- 1.3.6.1.4.1.17409.1.12
-- 1.3.6.1.4.1.17409.1.12
-- 1.3.6.1.4.1.17409.1.12
		-- 1.3.6.1.4.1.17409.1.12
		addIdent OBJECT IDENTIFIER ::= { nscrtvHFCemsTree 12 }

		
--         **********************************************************************************************
-- 双向射频放大器MIB
-- **********************************************************************************************
-- 1.3.6.1.4.1.1.1.12.1
-- 1.3.6.1.4.1.17409.1.12.1
-- 1.3.6.1.4.1.17409.1.12.1
-- 1.3.6.1.4.1.17409.1.12.1
-- 1.3.6.1.4.1.17409.1.12.1
-- 1.3.6.1.4.1.17409.1.12.1
-- 1.3.6.1.4.1.17409.1.12.1
-- 1.3.6.1.4.1.17409.1.12.1
		-- 1.3.6.1.4.1.17409.1.12.1
		addVendorOID OBJECT-TYPE
			SYNTAX OBJECT IDENTIFIER
			MAX-ACCESS read-only
			STATUS optional
			DESCRIPTION
				"此对象提供厂商对双向射频放大器MIB的扩充，无扩充时此对象应指向双向射频放大器节点addIdent。"
			::= { addIdent 1 }

		
--          ***********
-- * RF 端口
-- ***********
-- 1.3.6.1.4.1.1.1.12.2
-- 1.3.6.1.4.1.17409.1.12.2
-- 1.3.6.1.4.1.17409.1.12.2
-- 1.3.6.1.4.1.17409.1.12.2
-- 1.3.6.1.4.1.17409.1.12.2
-- 1.3.6.1.4.1.17409.1.12.2
-- 1.3.6.1.4.1.17409.1.12.2
-- 1.3.6.1.4.1.17409.1.12.2
		-- 1.3.6.1.4.1.17409.1.12.2
		addNumberRFPort OBJECT-TYPE
			SYNTAX INTEGER (1..8)
			MAX-ACCESS read-only
			STATUS current
			DESCRIPTION
				"RF端口数目"
			::= { addIdent 2 }

		
--         1.3.6.1.4.1.1.1.12.3
-- 1.3.6.1.4.1.17409.1.12.3
-- 1.3.6.1.4.1.17409.1.12.3
-- 1.3.6.1.4.1.17409.1.12.3
-- 1.3.6.1.4.1.17409.1.12.3
-- 1.3.6.1.4.1.17409.1.12.3
-- 1.3.6.1.4.1.17409.1.12.3
-- 1.3.6.1.4.1.17409.1.12.3
		-- 1.3.6.1.4.1.17409.1.12.3
		addPortMasterAttenuationControl OBJECT-TYPE
			SYNTAX INTEGER
				{
				none(1),
				low(2),
				high(3)
				}
			MAX-ACCESS read-write
			STATUS optional
			DESCRIPTION
				"报告和控制适用于所有端口的上行通道衰减开关的状态。
				none(1): 无衰减；
				low(2): 典型的低衰减值；该衰减值可能并不适用于所用端口；
				high(3): 典型的高衰减值；该衰减值可能并不适用于所用端口。
				此对象的访问不影响addRFPortReverseAttenuationControl对象的值"
			::= { addIdent 3 }

		
--         1.3.6.1.4.1.1.1.12.4
-- 1.3.6.1.4.1.17409.1.12.4
-- 1.3.6.1.4.1.17409.1.12.4
-- 1.3.6.1.4.1.17409.1.12.4
-- 1.3.6.1.4.1.17409.1.12.4
-- 1.3.6.1.4.1.17409.1.12.4
-- 1.3.6.1.4.1.17409.1.12.4
-- 1.3.6.1.4.1.17409.1.12.4
		-- 1.3.6.1.4.1.17409.1.12.4
		addRFPortTable OBJECT-TYPE
			SYNTAX SEQUENCE OF AddRFPortEntry
			MAX-ACCESS not-accessible
			STATUS current
			DESCRIPTION
				"RF端口信息表。"
			::= { addIdent 4 }

		
--         1.3.6.1.4.1.1.1.12.4.1
-- 1.3.6.1.4.1.17409.1.12.4.1
-- 1.3.6.1.4.1.17409.1.12.4.1
-- 1.3.6.1.4.1.17409.1.12.4.1
-- 1.3.6.1.4.1.17409.1.12.4.1
-- 1.3.6.1.4.1.17409.1.12.4.1
-- 1.3.6.1.4.1.17409.1.12.4.1
-- 1.3.6.1.4.1.17409.1.12.4.1
		-- 1.3.6.1.4.1.17409.1.12.4.1
		addRFPortEntry OBJECT-TYPE
			SYNTAX AddRFPortEntry
			MAX-ACCESS not-accessible
			STATUS current
			DESCRIPTION
				"RF端口信息表目。"
			INDEX { addRFPortIndex }
			::= { addRFPortTable 1 }

		
		AddRFPortEntry ::=
			SEQUENCE { 
				addRFPortIndex
					Integer32,
				addRFPortControlType
					INTEGER,
				addRFPortControlLevel
					Integer32,
				addRFPortOutputRFLevel
					INTEGER,
				addRFPortName
					DisplayString,
				addRFPortReverseAttenuationControl
					INTEGER,
				addRFPortPowerFeedStatus
					INTEGER
			 }

--         1.3.6.1.4.1.1.1.12.4.1.1
-- 1.3.6.1.4.1.17409.1.12.4.1.1
-- 1.3.6.1.4.1.17409.1.12.4.1.1
-- 1.3.6.1.4.1.17409.1.12.4.1.1
-- 1.3.6.1.4.1.17409.1.12.4.1.1
-- 1.3.6.1.4.1.17409.1.12.4.1.1
-- 1.3.6.1.4.1.17409.1.12.4.1.1
-- 1.3.6.1.4.1.17409.1.12.4.1.1
		-- 1.3.6.1.4.1.17409.1.12.4.1.1
		addRFPortIndex OBJECT-TYPE
			SYNTAX Integer32
			MAX-ACCESS read-only
			STATUS current
			DESCRIPTION
				"RF端口索引，索引编号可根据实际应用情况确定，可以表示第几个端口，也可以是端口的编号。"
			::= { addRFPortEntry 1 }

		
--         1.3.6.1.4.1.1.1.12.4.1.2
-- 1.3.6.1.4.1.17409.1.12.4.1.2
-- 1.3.6.1.4.1.17409.1.12.4.1.2
-- 1.3.6.1.4.1.17409.1.12.4.1.2
-- 1.3.6.1.4.1.17409.1.12.4.1.2
-- 1.3.6.1.4.1.17409.1.12.4.1.2
-- 1.3.6.1.4.1.17409.1.12.4.1.2
-- 1.3.6.1.4.1.17409.1.12.4.1.2
		-- 1.3.6.1.4.1.17409.1.12.4.1.2
		addRFPortControlType OBJECT-TYPE
			SYNTAX INTEGER
				{
				alc(1),
				asc(2),
				agc(3),
				none(4)
				}
			MAX-ACCESS read-only
			STATUS optional
			DESCRIPTION
				"控制类型：alc（自动电平控制），asc（自动斜率控制），agc（自动增益控制），none(无固定类型)。"
			::= { addRFPortEntry 2 }

		
--         1.3.6.1.4.1.1.1.12.4.1.3
-- 1.3.6.1.4.1.17409.1.12.4.1.3
-- 1.3.6.1.4.1.17409.1.12.4.1.3
-- 1.3.6.1.4.1.17409.1.12.4.1.3
-- 1.3.6.1.4.1.17409.1.12.4.1.3
-- 1.3.6.1.4.1.17409.1.12.4.1.3
-- 1.3.6.1.4.1.17409.1.12.4.1.3
-- 1.3.6.1.4.1.17409.1.12.4.1.3
		-- 1.3.6.1.4.1.17409.1.12.4.1.3
		addRFPortControlLevel OBJECT-TYPE
			SYNTAX Integer32
			MAX-ACCESS read-only
			STATUS optional
			DESCRIPTION
				"放大器RF端口控制类型指示的控制电平，单位为0.1VDC。
				此对象要求在属性MIB中登记一个条目。"
			::= { addRFPortEntry 3 }

		
--         1.3.6.1.4.1.1.1.12.4.1.4
-- 1.3.6.1.4.1.17409.1.12.4.1.4
-- 1.3.6.1.4.1.17409.1.12.4.1.4
-- 1.3.6.1.4.1.17409.1.12.4.1.4
-- 1.3.6.1.4.1.17409.1.12.4.1.4
-- 1.3.6.1.4.1.17409.1.12.4.1.4
-- 1.3.6.1.4.1.17409.1.12.4.1.4
-- 1.3.6.1.4.1.17409.1.12.4.1.4
		-- 1.3.6.1.4.1.17409.1.12.4.1.4
		addRFPortOutputRFLevel OBJECT-TYPE
			SYNTAX INTEGER (0..127)
			MAX-ACCESS read-only
			STATUS optional
			DESCRIPTION
				"放大器RF端口的导频输出电平，单位为dBuV。
				此对象要求在属性MIB中登记一个条目。"
			::= { addRFPortEntry 4 }

		
--         1.3.6.1.4.1.1.1.12.4.1.5
-- 1.3.6.1.4.1.17409.1.12.4.1.5
-- 1.3.6.1.4.1.17409.1.12.4.1.5
-- 1.3.6.1.4.1.17409.1.12.4.1.5
-- 1.3.6.1.4.1.17409.1.12.4.1.5
-- 1.3.6.1.4.1.17409.1.12.4.1.5
-- 1.3.6.1.4.1.17409.1.12.4.1.5
-- 1.3.6.1.4.1.17409.1.12.4.1.5
		-- 1.3.6.1.4.1.17409.1.12.4.1.5
		addRFPortName OBJECT-TYPE
			SYNTAX DisplayString
			MAX-ACCESS read-only
			STATUS current
			DESCRIPTION
				"端口的物理名称，例如端口1和端口2。
				当此表中的对象产生告警陷阱消息时，此名称将被填入hfcAlarmTrap的绑定对象alarmText中。"
			::= { addRFPortEntry 5 }

		
--         1.3.6.1.4.1.1.1.12.4.1.6
-- 1.3.6.1.4.1.17409.1.12.4.1.6
-- 1.3.6.1.4.1.17409.1.12.4.1.6
-- 1.3.6.1.4.1.17409.1.12.4.1.6
-- 1.3.6.1.4.1.17409.1.12.4.1.6
-- 1.3.6.1.4.1.17409.1.12.4.1.6
-- 1.3.6.1.4.1.17409.1.12.4.1.6
-- 1.3.6.1.4.1.17409.1.12.4.1.6
		-- 1.3.6.1.4.1.17409.1.12.4.1.6
		addRFPortReverseAttenuationControl OBJECT-TYPE
			SYNTAX INTEGER
				{
				none(1),
				low(2),
				high(3)
				}
			MAX-ACCESS read-write
			STATUS optional
			DESCRIPTION
				"报告和控制该端口的上行通道衰减开关的状态。
				none(1): 无衰减；
				low(2): 上行通道典型的低衰减值，该衰减值可能并不适用于所有开关。
				high(3): 上行通道典型的高衰减值，该衰减值可能并不适用于所用开关。"
			::= { addRFPortEntry 6 }

		
--         1.3.6.1.4.1.1.1.12.4.1.7
-- 1.3.6.1.4.1.17409.1.12.4.1.7
-- 1.3.6.1.4.1.17409.1.12.4.1.7
-- 1.3.6.1.4.1.17409.1.12.4.1.7
-- 1.3.6.1.4.1.17409.1.12.4.1.7
-- 1.3.6.1.4.1.17409.1.12.4.1.7
-- 1.3.6.1.4.1.17409.1.12.4.1.7
-- 1.3.6.1.4.1.17409.1.12.4.1.7
		-- 1.3.6.1.4.1.17409.1.12.4.1.7
		addRFPortPowerFeedStatus OBJECT-TYPE
			SYNTAX INTEGER
				{
				on(1),
				off(2)
				}
			MAX-ACCESS read-only
			STATUS optional
			DESCRIPTION
				"RF端口馈电状态，'1'表示有馈电，'2'表示无馈电。"
			::= { addRFPortEntry 7 }

		
--          ***********
-- * 交流电源
-- ***********
-- 1.3.6.1.4.1.1.1.12.5
-- 1.3.6.1.4.1.17409.1.12.5
-- 1.3.6.1.4.1.17409.1.12.5
-- 1.3.6.1.4.1.17409.1.12.5
-- 1.3.6.1.4.1.17409.1.12.5
-- 1.3.6.1.4.1.17409.1.12.5
-- 1.3.6.1.4.1.17409.1.12.5
-- 1.3.6.1.4.1.17409.1.12.5
		-- 1.3.6.1.4.1.17409.1.12.5
		addLinePowerVoltage1 OBJECT-TYPE
			SYNTAX INTEGER (0..65535)
			MAX-ACCESS read-only
			STATUS optional
			DESCRIPTION
				"线路电源电压。单位为1VAC。此对象要求在属性MIB中登记一个条目。"
			::= { addIdent 5 }

		
--         1.3.6.1.4.1.1.1.12.6
-- 1.3.6.1.4.1.17409.1.12.6
-- 1.3.6.1.4.1.17409.1.12.6
-- 1.3.6.1.4.1.17409.1.12.6
-- 1.3.6.1.4.1.17409.1.12.6
-- 1.3.6.1.4.1.17409.1.12.6
-- 1.3.6.1.4.1.17409.1.12.6
-- 1.3.6.1.4.1.17409.1.12.6
		-- 1.3.6.1.4.1.17409.1.12.6
		addLinePowerVoltage2 OBJECT-TYPE
			SYNTAX INTEGER (0..65535)
			MAX-ACCESS read-only
			STATUS optional
			DESCRIPTION
				"备份线路电源电压，单位为1VAC。此对象要求在属性MIB中登记一个条目。"
			::= { addIdent 6 }

		
--         1.3.6.1.4.1.1.1.12.7
-- 1.3.6.1.4.1.17409.1.12.7
-- 1.3.6.1.4.1.17409.1.12.7
-- 1.3.6.1.4.1.17409.1.12.7
-- 1.3.6.1.4.1.17409.1.12.7
-- 1.3.6.1.4.1.17409.1.12.7
-- 1.3.6.1.4.1.17409.1.12.7
-- 1.3.6.1.4.1.17409.1.12.7
		-- 1.3.6.1.4.1.17409.1.12.7
		addLinePowerCurrent OBJECT-TYPE
			SYNTAX INTEGER (0..65535)
			MAX-ACCESS read-only
			STATUS optional
			DESCRIPTION
				"放大器的总电流，单位为0.1A。此对象要求在属性MIB中登记一个条目。"
			::= { addIdent 7 }

		
--          *****************
-- * 直流电源
-- *****************
-- 1.3.6.1.4.1.1.1.12.8
-- 1.3.6.1.4.1.17409.1.12.8
-- 1.3.6.1.4.1.17409.1.12.8
-- 1.3.6.1.4.1.17409.1.12.8
-- 1.3.6.1.4.1.17409.1.12.8
-- 1.3.6.1.4.1.17409.1.12.8
-- 1.3.6.1.4.1.17409.1.12.8
-- 1.3.6.1.4.1.17409.1.12.8
		-- 1.3.6.1.4.1.17409.1.12.8
		addNumberDCPowerSupply OBJECT-TYPE
			SYNTAX INTEGER (0..16)
			MAX-ACCESS read-only
			STATUS current
			DESCRIPTION
				"内部直流电源的数目，'0'表示设备无此功能。"
			::= { addIdent 8 }

		
--         1.3.6.1.4.1.1.1.12.9
-- 1.3.6.1.4.1.17409.1.12.9
-- 1.3.6.1.4.1.17409.1.12.9
-- 1.3.6.1.4.1.17409.1.12.9
-- 1.3.6.1.4.1.17409.1.12.9
-- 1.3.6.1.4.1.17409.1.12.9
-- 1.3.6.1.4.1.17409.1.12.9
-- 1.3.6.1.4.1.17409.1.12.9
		-- 1.3.6.1.4.1.17409.1.12.9
		addDCPowerSupplyMode OBJECT-TYPE
			SYNTAX INTEGER
				{
				loadsharing(1),
				switchedRedundant(2),
				aloneSupply(3)
				}
			MAX-ACCESS read-only
			STATUS optional
			DESCRIPTION
				"供电电源工作模式：负载分担、备用切换或独立供电。"
			::= { addIdent 9 }

		
--         1.3.6.1.4.1.1.1.12.10
-- 1.3.6.1.4.1.17409.1.12.10
-- 1.3.6.1.4.1.17409.1.12.10
-- 1.3.6.1.4.1.17409.1.12.10
-- 1.3.6.1.4.1.17409.1.12.10
-- 1.3.6.1.4.1.17409.1.12.10
-- 1.3.6.1.4.1.17409.1.12.10
-- 1.3.6.1.4.1.17409.1.12.10
		-- 1.3.6.1.4.1.17409.1.12.10
		addDCPowerTable OBJECT-TYPE
			SYNTAX SEQUENCE OF AddDCPowerEntry
			MAX-ACCESS not-accessible
			STATUS current
			DESCRIPTION
				"直流电源信息表。"
			::= { addIdent 10 }

		
--         1.3.6.1.4.1.1.1.12.10.1
-- 1.3.6.1.4.1.17409.1.12.10.1
-- 1.3.6.1.4.1.17409.1.12.10.1
-- 1.3.6.1.4.1.17409.1.12.10.1
-- 1.3.6.1.4.1.17409.1.12.10.1
-- 1.3.6.1.4.1.17409.1.12.10.1
-- 1.3.6.1.4.1.17409.1.12.10.1
-- 1.3.6.1.4.1.17409.1.12.10.1
		-- 1.3.6.1.4.1.17409.1.12.10.1
		addDCPowerEntry OBJECT-TYPE
			SYNTAX AddDCPowerEntry
			MAX-ACCESS not-accessible
			STATUS current
			DESCRIPTION
				"直流电源信息表目。"
			INDEX { addDCPowerIndex }
			::= { addDCPowerTable 1 }

		
		AddDCPowerEntry ::=
			SEQUENCE { 
				addDCPowerIndex
					Integer32,
				addDCPowerVoltage
					INTEGER,
				addDCPowerCurrent
					INTEGER,
				addDCPowerName
					DisplayString
			 }

--         1.3.6.1.4.1.1.1.12.10.1.1
-- 1.3.6.1.4.1.17409.1.12.10.1.1
-- 1.3.6.1.4.1.17409.1.12.10.1.1
-- 1.3.6.1.4.1.17409.1.12.10.1.1
-- 1.3.6.1.4.1.17409.1.12.10.1.1
-- 1.3.6.1.4.1.17409.1.12.10.1.1
-- 1.3.6.1.4.1.17409.1.12.10.1.1
-- 1.3.6.1.4.1.17409.1.12.10.1.1
		-- 1.3.6.1.4.1.17409.1.12.10.1.1
		addDCPowerIndex OBJECT-TYPE
			SYNTAX Integer32
			MAX-ACCESS read-only
			STATUS current
			DESCRIPTION
				"直流电源索引。"
			::= { addDCPowerEntry 1 }

		
--         1.3.6.1.4.1.1.1.12.10.1.2
-- 1.3.6.1.4.1.17409.1.12.10.1.2
-- 1.3.6.1.4.1.17409.1.12.10.1.2
-- 1.3.6.1.4.1.17409.1.12.10.1.2
-- 1.3.6.1.4.1.17409.1.12.10.1.2
-- 1.3.6.1.4.1.17409.1.12.10.1.2
-- 1.3.6.1.4.1.17409.1.12.10.1.2
-- 1.3.6.1.4.1.17409.1.12.10.1.2
		-- 1.3.6.1.4.1.17409.1.12.10.1.2
		addDCPowerVoltage OBJECT-TYPE
			SYNTAX INTEGER (-32768..32767)
			MAX-ACCESS read-only
			STATUS current
			DESCRIPTION
				"电源电压，单位为0.1V。此对象要求在属性MIB中登记一个条目。"
			::= { addDCPowerEntry 2 }

		
--         1.3.6.1.4.1.1.1.12.10.1.3
-- 1.3.6.1.4.1.17409.1.12.10.1.3
-- 1.3.6.1.4.1.17409.1.12.10.1.3
-- 1.3.6.1.4.1.17409.1.12.10.1.3
-- 1.3.6.1.4.1.17409.1.12.10.1.3
-- 1.3.6.1.4.1.17409.1.12.10.1.3
-- 1.3.6.1.4.1.17409.1.12.10.1.3
-- 1.3.6.1.4.1.17409.1.12.10.1.3
		-- 1.3.6.1.4.1.17409.1.12.10.1.3
		addDCPowerCurrent OBJECT-TYPE
			SYNTAX INTEGER (0..65535)
			MAX-ACCESS read-only
			STATUS optional
			DESCRIPTION
				"电源电流，单位为0.1A。此对象要求在属性MIB中登记一个条目。"
			::= { addDCPowerEntry 3 }

		
--         1.3.6.1.4.1.1.1.12.10.1.4
-- 1.3.6.1.4.1.17409.1.12.10.1.4
-- 1.3.6.1.4.1.17409.1.12.10.1.4
-- 1.3.6.1.4.1.17409.1.12.10.1.4
-- 1.3.6.1.4.1.17409.1.12.10.1.4
-- 1.3.6.1.4.1.17409.1.12.10.1.4
-- 1.3.6.1.4.1.17409.1.12.10.1.4
-- 1.3.6.1.4.1.17409.1.12.10.1.4
		-- 1.3.6.1.4.1.17409.1.12.10.1.4
		addDCPowerName OBJECT-TYPE
			SYNTAX DisplayString
			MAX-ACCESS read-only
			STATUS current
			DESCRIPTION
				"标明直流电源名称，例如：24V直流电源A。
				此字段值由用户规定，至少应标明工作电压并将多个电源相互区分开。
				当此表中的对象产生告警时，此对象名称应放进hfcAlarmEvent陷阱的alarmText对象里。"
			::= { addDCPowerEntry 4 }

		
--              DESCRIPTION
-- "双向射频放大器(Amplifier of Dual Direction)MIB的分支节点标识。"
-- "见附录N。"
-- 1.3.6.1.4.1.1.1.13
-- 1.3.6.1.4.1.17409.1.13
-- 1.3.6.1.4.1.17409.1.13
-- 1.3.6.1.4.1.17409.1.13
-- 1.3.6.1.4.1.17409.1.13
-- 1.3.6.1.4.1.17409.1.13
-- 1.3.6.1.4.1.17409.1.13
-- 1.3.6.1.4.1.17409.1.13
		-- 1.3.6.1.4.1.17409.1.13
		cacIdent OBJECT IDENTIFIER ::= { nscrtvHFCemsTree 13 }

		
--         *********************************************************************************************
-- 可寻址终端控制器MIB
-- *********************************************************************************************
-- 1.3.6.1.4.1.1.1.13.1
-- 1.3.6.1.4.1.17409.1.13.1
-- 1.3.6.1.4.1.17409.1.13.1
-- 1.3.6.1.4.1.17409.1.13.1
-- 1.3.6.1.4.1.17409.1.13.1
-- 1.3.6.1.4.1.17409.1.13.1
-- 1.3.6.1.4.1.17409.1.13.1
-- 1.3.6.1.4.1.17409.1.13.1
		-- 1.3.6.1.4.1.17409.1.13.1
		cacVendorOID OBJECT-TYPE
			SYNTAX OBJECT IDENTIFIER
			MAX-ACCESS read-only
			STATUS optional
			DESCRIPTION
				"此对象提供厂商对可寻址终端控制器MIB的扩充，无扩充时此对象应指向可寻址终端控制器节点cacIdent。"
			::= { cacIdent 1 }

		
--          ****************
-- * 工作参数
-- ****************
-- 1.3.6.1.4.1.1.1.13.2
-- 1.3.6.1.4.1.17409.1.13.2
-- 1.3.6.1.4.1.17409.1.13.2
-- 1.3.6.1.4.1.17409.1.13.2
-- 1.3.6.1.4.1.17409.1.13.2
-- 1.3.6.1.4.1.17409.1.13.2
-- 1.3.6.1.4.1.17409.1.13.2
-- 1.3.6.1.4.1.17409.1.13.2
		-- 1.3.6.1.4.1.17409.1.13.2
		cacPowerType OBJECT-TYPE
			SYNTAX INTEGER
				{
				v60(1),
				v220(2),
				other(3)
				}
			MAX-ACCESS read-only
			STATUS current
			DESCRIPTION
				"供电类型：'1'表示60V芯线供电，'2'表示220V市电供电，'3'表示其它。"
			::= { cacIdent 2 }

		
--         1.3.6.1.4.1.1.1.13.3
-- 1.3.6.1.4.1.17409.1.13.3
-- 1.3.6.1.4.1.17409.1.13.3
-- 1.3.6.1.4.1.17409.1.13.3
-- 1.3.6.1.4.1.17409.1.13.3
-- 1.3.6.1.4.1.17409.1.13.3
-- 1.3.6.1.4.1.17409.1.13.3
-- 1.3.6.1.4.1.17409.1.13.3
		-- 1.3.6.1.4.1.17409.1.13.3
		cacACPowerVoltage OBJECT-TYPE
			SYNTAX INTEGER (0..32767)
			MAX-ACCESS read-only
			STATUS optional
			DESCRIPTION
				"交流供电电压, 单位为0.1V，此对象要求在属性MIB中登记一个条目。"
			::= { cacIdent 3 }

		
--         1.3.6.1.4.1.1.1.13.4
-- 1.3.6.1.4.1.17409.1.13.4
-- 1.3.6.1.4.1.17409.1.13.4
-- 1.3.6.1.4.1.17409.1.13.4
-- 1.3.6.1.4.1.17409.1.13.4
-- 1.3.6.1.4.1.17409.1.13.4
-- 1.3.6.1.4.1.17409.1.13.4
-- 1.3.6.1.4.1.17409.1.13.4
		-- 1.3.6.1.4.1.17409.1.13.4
		cacMainDCPowerVoltage OBJECT-TYPE
			SYNTAX INTEGER (-32768..32767)
			MAX-ACCESS read-only
			STATUS current
			DESCRIPTION
				"主直流工作电压,单位为0.1V。此对象要求在属性MIB中登记一个条目。"
			::= { cacIdent 4 }

		
--         1.3.6.1.4.1.1.1.13.5
-- 1.3.6.1.4.1.17409.1.13.5
-- 1.3.6.1.4.1.17409.1.13.5
-- 1.3.6.1.4.1.17409.1.13.5
-- 1.3.6.1.4.1.17409.1.13.5
-- 1.3.6.1.4.1.17409.1.13.5
-- 1.3.6.1.4.1.17409.1.13.5
-- 1.3.6.1.4.1.17409.1.13.5
		-- 1.3.6.1.4.1.17409.1.13.5
		cacInsideAmpOutputRFLevel OBJECT-TYPE
			SYNTAX INTEGER (0..127)
			MAX-ACCESS read-only
			STATUS current
			DESCRIPTION
				"内置放大器导频输出电平,单位为dBuV。此对象要求在属性MIB中登记一个条目。"
			::= { cacIdent 5 }

		
--         1.3.6.1.4.1.1.1.13.6
-- 1.3.6.1.4.1.17409.1.13.6
-- 1.3.6.1.4.1.17409.1.13.6
-- 1.3.6.1.4.1.17409.1.13.6
-- 1.3.6.1.4.1.17409.1.13.6
-- 1.3.6.1.4.1.17409.1.13.6
-- 1.3.6.1.4.1.17409.1.13.6
-- 1.3.6.1.4.1.17409.1.13.6
		-- 1.3.6.1.4.1.17409.1.13.6
		cacUpStreamControl OBJECT-TYPE
			SYNTAX INTEGER
				{
				on(1),
				off(2)
				}
			MAX-ACCESS read-write
			STATUS current
			DESCRIPTION
				"上行通道状态。"
			::= { cacIdent 6 }

		
--         1.3.6.1.4.1.1.1.13.7
-- 1.3.6.1.4.1.17409.1.13.7
-- 1.3.6.1.4.1.17409.1.13.7
-- 1.3.6.1.4.1.17409.1.13.7
-- 1.3.6.1.4.1.17409.1.13.7
-- 1.3.6.1.4.1.17409.1.13.7
-- 1.3.6.1.4.1.17409.1.13.7
-- 1.3.6.1.4.1.17409.1.13.7
		-- 1.3.6.1.4.1.17409.1.13.7
		cacOutputPortNumber OBJECT-TYPE
			SYNTAX INTEGER (1..127)
			MAX-ACCESS read-only
			STATUS current
			DESCRIPTION
				"输出端口数。"
			::= { cacIdent 7 }

		
--         1.3.6.1.4.1.1.1.13.8
-- 1.3.6.1.4.1.17409.1.13.8
-- 1.3.6.1.4.1.17409.1.13.8
-- 1.3.6.1.4.1.17409.1.13.8
-- 1.3.6.1.4.1.17409.1.13.8
-- 1.3.6.1.4.1.17409.1.13.8
-- 1.3.6.1.4.1.17409.1.13.8
-- 1.3.6.1.4.1.17409.1.13.8
		-- 1.3.6.1.4.1.17409.1.13.8
		cacPortTable OBJECT-TYPE
			SYNTAX SEQUENCE OF CacPortTableEntry
			MAX-ACCESS not-accessible
			STATUS current
			DESCRIPTION
				"端口信息表。"
			::= { cacIdent 8 }

		
--         1.3.6.1.4.1.1.1.13.8.1
-- 1.3.6.1.4.1.17409.1.13.8.1
-- 1.3.6.1.4.1.17409.1.13.8.1
-- 1.3.6.1.4.1.17409.1.13.8.1
-- 1.3.6.1.4.1.17409.1.13.8.1
-- 1.3.6.1.4.1.17409.1.13.8.1
-- 1.3.6.1.4.1.17409.1.13.8.1
-- 1.3.6.1.4.1.17409.1.13.8.1
		-- 1.3.6.1.4.1.17409.1.13.8.1
		cacPortTableEntry OBJECT-TYPE
			SYNTAX CacPortTableEntry
			MAX-ACCESS not-accessible
			STATUS current
			DESCRIPTION
				"各端口信息表目。"
			INDEX { cacPortIndex }
			::= { cacPortTable 1 }

		
		CacPortTableEntry ::=
			SEQUENCE { 
				cacPortIndex
					INTEGER,
				cacPortControl
					OCTET STRING,
				cacPortRFLevel
					INTEGER
			 }

--         1.3.6.1.4.1.1.1.13.8.1.1
-- 1.3.6.1.4.1.17409.1.13.8.1.1
-- 1.3.6.1.4.1.17409.1.13.8.1.1
-- 1.3.6.1.4.1.17409.1.13.8.1.1
-- 1.3.6.1.4.1.17409.1.13.8.1.1
-- 1.3.6.1.4.1.17409.1.13.8.1.1
-- 1.3.6.1.4.1.17409.1.13.8.1.1
-- 1.3.6.1.4.1.17409.1.13.8.1.1
		-- 1.3.6.1.4.1.17409.1.13.8.1.1
		cacPortIndex OBJECT-TYPE
			SYNTAX INTEGER (1..127)
			MAX-ACCESS read-only
			STATUS current
			DESCRIPTION
				"端口号索引。"
			::= { cacPortTableEntry 1 }

		
--         1.3.6.1.4.1.1.1.13.8.1.2
-- 1.3.6.1.4.1.17409.1.13.8.1.2
-- 1.3.6.1.4.1.17409.1.13.8.1.2
-- 1.3.6.1.4.1.17409.1.13.8.1.2
-- 1.3.6.1.4.1.17409.1.13.8.1.2
-- 1.3.6.1.4.1.17409.1.13.8.1.2
-- 1.3.6.1.4.1.17409.1.13.8.1.2
-- 1.3.6.1.4.1.17409.1.13.8.1.2
		-- 1.3.6.1.4.1.17409.1.13.8.1.2
		cacPortControl OBJECT-TYPE
			SYNTAX OCTET STRING
			MAX-ACCESS read-write
			STATUS current
			DESCRIPTION
				"端口下行射频通道状态。
				bit7表示该状态是否写入非易失性存储器，bit7=1表示需要写入非易失性存储器，bit7=0表示不需要写入非易失性存储器。
				端口状态表示如下：'1'非记忆全频段开，'2'非记忆全频段关，'3～15'非记忆限制状态，'16～127'预留，'129'记忆全频段开，'130'记忆全频段关，'131～143'记忆限制状态，'144～255'预留。"
			::= { cacPortTableEntry 2 }

		
--         1.3.6.1.4.1.1.1.13.8.1.3
-- 1.3.6.1.4.1.17409.1.13.8.1.3
-- 1.3.6.1.4.1.17409.1.13.8.1.3
-- 1.3.6.1.4.1.17409.1.13.8.1.3
-- 1.3.6.1.4.1.17409.1.13.8.1.3
-- 1.3.6.1.4.1.17409.1.13.8.1.3
-- 1.3.6.1.4.1.17409.1.13.8.1.3
-- 1.3.6.1.4.1.17409.1.13.8.1.3
		-- 1.3.6.1.4.1.17409.1.13.8.1.3
		cacPortRFLevel OBJECT-TYPE
			SYNTAX INTEGER (0..127)
			MAX-ACCESS read-only
			STATUS optional
			DESCRIPTION
				"端口下行信道射频电平,单位为dBuV。"
			::= { cacPortTableEntry 3 }

		
--         1.3.6.1.4.1.1.1.13.9
-- 1.3.6.1.4.1.17409.1.13.9
-- 1.3.6.1.4.1.17409.1.13.9
-- 1.3.6.1.4.1.17409.1.13.9
-- 1.3.6.1.4.1.17409.1.13.9
-- 1.3.6.1.4.1.17409.1.13.9
-- 1.3.6.1.4.1.17409.1.13.9
-- 1.3.6.1.4.1.17409.1.13.9
		-- 1.3.6.1.4.1.17409.1.13.9
		cacAllPortsState OBJECT-TYPE
			SYNTAX OCTET STRING (SIZE (1..255))
			MAX-ACCESS read-write
			STATUS optional
			DESCRIPTION
				"所有端口状态，字节位置与端口序号对应，如第5字节表示第5端口状态，各端口状态与cacPortControl相同"
			::= { cacIdent 9 }

		
--         1.3.6.1.4.1.1.1.13.10
-- 1.3.6.1.4.1.17409.1.13.10
-- 1.3.6.1.4.1.17409.1.13.10
-- 1.3.6.1.4.1.17409.1.13.10
-- 1.3.6.1.4.1.17409.1.13.10
-- 1.3.6.1.4.1.17409.1.13.10
-- 1.3.6.1.4.1.17409.1.13.10
-- 1.3.6.1.4.1.17409.1.13.10
		-- 1.3.6.1.4.1.17409.1.13.10
		cacPortStateReset OBJECT-TYPE
			SYNTAX Integer32
			MAX-ACCESS read-write
			STATUS optional
			DESCRIPTION
				"端口状态复位，写入'1'后所有端口恢复到非易失性存储器中存储的端口状态，写入其它值将不起作用。读此对象时返回值'1'，对设备无影响。写入'1'时不导致设备硬件复位。"
			::= { cacIdent 10 }

		
--              DESCRIPTION
-- "可寻址终端控制器(Controlled Access-Controller)MIB的分支节点标识。"
-- "见附录O。"
-- 1.3.6.1.4.1.1.1.14
-- 1.3.6.1.4.1.17409.1.14
-- 1.3.6.1.4.1.17409.1.14
-- 1.3.6.1.4.1.17409.1.14
-- 1.3.6.1.4.1.17409.1.14
-- 1.3.6.1.4.1.17409.1.14
-- 1.3.6.1.4.1.17409.1.14
-- 1.3.6.1.4.1.17409.1.14
		-- 1.3.6.1.4.1.17409.1.14
		lineIdent OBJECT IDENTIFIER ::= { nscrtvHFCemsTree 14 }

		
--         *********************************************************************************************
-- 线路MIB
-- *********************************************************************************************
-- 1.3.6.1.4.1.1.1.14.1
-- 1.3.6.1.4.1.17409.1.14.1
-- 1.3.6.1.4.1.17409.1.14.1
-- 1.3.6.1.4.1.17409.1.14.1
-- 1.3.6.1.4.1.17409.1.14.1
-- 1.3.6.1.4.1.17409.1.14.1
-- 1.3.6.1.4.1.17409.1.14.1
-- 1.3.6.1.4.1.17409.1.14.1
		-- 1.3.6.1.4.1.17409.1.14.1
		lineVendorOID OBJECT-TYPE
			SYNTAX OBJECT IDENTIFIER
			MAX-ACCESS read-only
			STATUS optional
			DESCRIPTION
				"此对象提供厂商对线路MIB的扩充，无扩充时此对象应指向线路MIB节点lineIdent。"
			::= { lineIdent 1 }

		
--          ***********
-- * RF电平
-- ***********
-- 1.3.6.1.4.1.1.1.14.2
-- 1.3.6.1.4.1.17409.1.14.2
-- 1.3.6.1.4.1.17409.1.14.2
-- 1.3.6.1.4.1.17409.1.14.2
-- 1.3.6.1.4.1.17409.1.14.2
-- 1.3.6.1.4.1.17409.1.14.2
-- 1.3.6.1.4.1.17409.1.14.2
-- 1.3.6.1.4.1.17409.1.14.2
		-- 1.3.6.1.4.1.17409.1.14.2
		lineRFLevel OBJECT-TYPE
			SYNTAX INTEGER (0..127)
			MAX-ACCESS read-only
			STATUS current
			DESCRIPTION
				"RF导频输出电平，单位为dBuV。
				此对象要求在属性MIB中登记一个条目。"
			::= { lineIdent 2 }

		
--          ***********
-- * 交流电源
-- ***********
-- 1.3.6.1.4.1.1.1.14.3
-- 1.3.6.1.4.1.17409.1.14.3
-- 1.3.6.1.4.1.17409.1.14.3
-- 1.3.6.1.4.1.17409.1.14.3
-- 1.3.6.1.4.1.17409.1.14.3
-- 1.3.6.1.4.1.17409.1.14.3
-- 1.3.6.1.4.1.17409.1.14.3
-- 1.3.6.1.4.1.17409.1.14.3
		-- 1.3.6.1.4.1.17409.1.14.3
		lineLinePowerVoltage OBJECT-TYPE
			SYNTAX INTEGER (0..65535)
			MAX-ACCESS read-only
			STATUS optional
			DESCRIPTION
				"线路馈电电压，单位为1VAC。此对象要求在属性MIB中登记一个条目。"
			::= { lineIdent 3 }

		
--         1.3.6.1.4.1.1.1.14.4
-- 1.3.6.1.4.1.17409.1.14.4
-- 1.3.6.1.4.1.17409.1.14.4
-- 1.3.6.1.4.1.17409.1.14.4
-- 1.3.6.1.4.1.17409.1.14.4
-- 1.3.6.1.4.1.17409.1.14.4
-- 1.3.6.1.4.1.17409.1.14.4
-- 1.3.6.1.4.1.17409.1.14.4
		-- 1.3.6.1.4.1.17409.1.14.4
		lineLinePowerCurrent OBJECT-TYPE
			SYNTAX INTEGER (0..65535)
			MAX-ACCESS read-only
			STATUS optional
			DESCRIPTION
				"线路馈电电流，单位为0.1mA。此对象要求在属性MIB中登记一个条目。"
			::= { lineIdent 4 }

		
--          *****************
-- * 直流电源
-- *****************
-- 1.3.6.1.4.1.1.1.14.5
-- 1.3.6.1.4.1.17409.1.14.5
-- 1.3.6.1.4.1.17409.1.14.5
-- 1.3.6.1.4.1.17409.1.14.5
-- 1.3.6.1.4.1.17409.1.14.5
-- 1.3.6.1.4.1.17409.1.14.5
-- 1.3.6.1.4.1.17409.1.14.5
-- 1.3.6.1.4.1.17409.1.14.5
		-- 1.3.6.1.4.1.17409.1.14.5
		lineNumberDCPowerSupply OBJECT-TYPE
			SYNTAX INTEGER (0..16)
			MAX-ACCESS read-only
			STATUS current
			DESCRIPTION
				"内部直流电源的数目，'0'表示设备无此功能。"
			::= { lineIdent 5 }

		
--         1.3.6.1.4.1.1.1.14.6
-- 1.3.6.1.4.1.17409.1.14.6
-- 1.3.6.1.4.1.17409.1.14.6
-- 1.3.6.1.4.1.17409.1.14.6
-- 1.3.6.1.4.1.17409.1.14.6
-- 1.3.6.1.4.1.17409.1.14.6
-- 1.3.6.1.4.1.17409.1.14.6
-- 1.3.6.1.4.1.17409.1.14.6
		-- 1.3.6.1.4.1.17409.1.14.6
		lineDCPowerTable OBJECT-TYPE
			SYNTAX SEQUENCE OF LineDCPowerEntry
			MAX-ACCESS not-accessible
			STATUS current
			DESCRIPTION
				"直流电源信息表。"
			::= { lineIdent 6 }

		
--         1.3.6.1.4.1.1.1.14.6.1
-- 1.3.6.1.4.1.17409.1.14.6.1
-- 1.3.6.1.4.1.17409.1.14.6.1
-- 1.3.6.1.4.1.17409.1.14.6.1
-- 1.3.6.1.4.1.17409.1.14.6.1
-- 1.3.6.1.4.1.17409.1.14.6.1
-- 1.3.6.1.4.1.17409.1.14.6.1
-- 1.3.6.1.4.1.17409.1.14.6.1
		-- 1.3.6.1.4.1.17409.1.14.6.1
		lineDCPowerEntry OBJECT-TYPE
			SYNTAX LineDCPowerEntry
			MAX-ACCESS not-accessible
			STATUS current
			DESCRIPTION
				"直流电源信息表目。"
			INDEX { lineDCPowerIndex }
			::= { lineDCPowerTable 1 }

		
		LineDCPowerEntry ::=
			SEQUENCE { 
				lineDCPowerIndex
					Integer32,
				lineDCPowerVoltage
					INTEGER,
				lineDCPowerCurrent
					INTEGER,
				lineDCPowerName
					DisplayString
			 }

--         1.3.6.1.4.1.1.1.14.6.1.1
-- 1.3.6.1.4.1.17409.1.14.6.1.1
-- 1.3.6.1.4.1.17409.1.14.6.1.1
-- 1.3.6.1.4.1.17409.1.14.6.1.1
-- 1.3.6.1.4.1.17409.1.14.6.1.1
-- 1.3.6.1.4.1.17409.1.14.6.1.1
-- 1.3.6.1.4.1.17409.1.14.6.1.1
-- 1.3.6.1.4.1.17409.1.14.6.1.1
		-- 1.3.6.1.4.1.17409.1.14.6.1.1
		lineDCPowerIndex OBJECT-TYPE
			SYNTAX Integer32
			MAX-ACCESS read-only
			STATUS current
			DESCRIPTION
				"直流电源索引。"
			::= { lineDCPowerEntry 1 }

		
--         1.3.6.1.4.1.1.1.14.6.1.2
-- 1.3.6.1.4.1.17409.1.14.6.1.2
-- 1.3.6.1.4.1.17409.1.14.6.1.2
-- 1.3.6.1.4.1.17409.1.14.6.1.2
-- 1.3.6.1.4.1.17409.1.14.6.1.2
-- 1.3.6.1.4.1.17409.1.14.6.1.2
-- 1.3.6.1.4.1.17409.1.14.6.1.2
-- 1.3.6.1.4.1.17409.1.14.6.1.2
		-- 1.3.6.1.4.1.17409.1.14.6.1.2
		lineDCPowerVoltage OBJECT-TYPE
			SYNTAX INTEGER (-32768..32767)
			MAX-ACCESS read-only
			STATUS current
			DESCRIPTION
				"电源电压，单位为0.1V。此对象要求在属性MIB中登记一个条目。"
			::= { lineDCPowerEntry 2 }

		
--         1.3.6.1.4.1.1.1.14.6.1.3
-- 1.3.6.1.4.1.17409.1.14.6.1.3
-- 1.3.6.1.4.1.17409.1.14.6.1.3
-- 1.3.6.1.4.1.17409.1.14.6.1.3
-- 1.3.6.1.4.1.17409.1.14.6.1.3
-- 1.3.6.1.4.1.17409.1.14.6.1.3
-- 1.3.6.1.4.1.17409.1.14.6.1.3
-- 1.3.6.1.4.1.17409.1.14.6.1.3
		-- 1.3.6.1.4.1.17409.1.14.6.1.3
		lineDCPowerCurrent OBJECT-TYPE
			SYNTAX INTEGER (0..65535)
			MAX-ACCESS read-only
			STATUS optional
			DESCRIPTION
				"电源的电流，单位为0.1A。此对象要求在属性MIB中登记一个条目。"
			::= { lineDCPowerEntry 3 }

		
--         1.3.6.1.4.1.1.1.14.6.1.4
-- 1.3.6.1.4.1.17409.1.14.6.1.4
-- 1.3.6.1.4.1.17409.1.14.6.1.4
-- 1.3.6.1.4.1.17409.1.14.6.1.4
-- 1.3.6.1.4.1.17409.1.14.6.1.4
-- 1.3.6.1.4.1.17409.1.14.6.1.4
-- 1.3.6.1.4.1.17409.1.14.6.1.4
-- 1.3.6.1.4.1.17409.1.14.6.1.4
		-- 1.3.6.1.4.1.17409.1.14.6.1.4
		lineDCPowerName OBJECT-TYPE
			SYNTAX DisplayString
			MAX-ACCESS read-only
			STATUS current
			DESCRIPTION
				"标明该电源的名称，例如：24V直流电源A。
				此字段值由用户规定，至少应标明工作电压并将多个电源相互区分开。
				当此表中的对象产生告警时，此对象名称应放进hfcAlarmEvent陷阱的alarmText对象里。"
			::= { lineDCPowerEntry 4 }

		
--        1.3.6.1.4.1.17409.1.15
-- 1.3.6.1.4.1.17409.1.15
-- 1.3.6.1.4.1.17409.1.15
-- 1.3.6.1.4.1.17409.1.15
-- 1.3.6.1.4.1.17409.1.15
-- 1.3.6.1.4.1.17409.1.15
-- 1.3.6.1.4.1.17409.1.15
		-- 1.3.6.1.4.1.17409.1.15
		miscIdent OBJECT IDENTIFIER ::= { nscrtvHFCemsTree 15 }

		
--        1.3.6.1.4.1.17409.1.15.1
-- 1.3.6.1.4.1.17409.1.15.1
-- 1.3.6.1.4.1.17409.1.15.1
-- 1.3.6.1.4.1.17409.1.15.1
-- 1.3.6.1.4.1.17409.1.15.1
-- 1.3.6.1.4.1.17409.1.15.1
-- 1.3.6.1.4.1.17409.1.15.1
		-- 1.3.6.1.4.1.17409.1.15.1
		comDeviceVoltage12V OBJECT-TYPE
			SYNTAX OCTET STRING
			MAX-ACCESS read-only
			STATUS current
			DESCRIPTION
				"Description."
			::= { miscIdent 1 }

		
--        1.3.6.1.4.1.17409.1.15.2
-- 1.3.6.1.4.1.17409.1.15.2
-- 1.3.6.1.4.1.17409.1.15.2
-- 1.3.6.1.4.1.17409.1.15.2
-- 1.3.6.1.4.1.17409.1.15.2
-- 1.3.6.1.4.1.17409.1.15.2
-- 1.3.6.1.4.1.17409.1.15.2
		-- 1.3.6.1.4.1.17409.1.15.2
		comDeviceRFAttenuation OBJECT-TYPE
			SYNTAX Integer32 (0..6)
			MAX-ACCESS read-write
			STATUS current
			DESCRIPTION
				"Description."
			::= { miscIdent 2 }

		
--        1.3.6.1.4.1.17409.1.15.3
-- 1.3.6.1.4.1.17409.1.15.3
-- 1.3.6.1.4.1.17409.1.15.3
-- 1.3.6.1.4.1.17409.1.15.3
-- 1.3.6.1.4.1.17409.1.15.3
-- 1.3.6.1.4.1.17409.1.15.3
-- 1.3.6.1.4.1.17409.1.15.3
		-- 1.3.6.1.4.1.17409.1.15.3
		comDeviceVersionInfo OBJECT-TYPE
			SYNTAX OCTET STRING
			MAX-ACCESS read-only
			STATUS current
			DESCRIPTION
				"Description."
			::= { miscIdent 3 }

		
--       1.3.6.1.4.1.17409.1.16
-- 1.3.6.1.4.1.17409.1.16
-- 1.3.6.1.4.1.17409.1.16
-- 1.3.6.1.4.1.17409.1.16
-- 1.3.6.1.4.1.17409.1.16
-- 1.3.6.1.4.1.17409.1.16
		-- 1.3.6.1.4.1.17409.1.16
		cltConfigRemoteUpgrade OBJECT IDENTIFIER ::= { nscrtvHFCemsTree 16 }

		
--       1.3.6.1.4.1.17409.1.16.1
-- 1.3.6.1.4.1.17409.1.16.1
-- 1.3.6.1.4.1.17409.1.16.1
-- 1.3.6.1.4.1.17409.1.16.1
-- 1.3.6.1.4.1.17409.1.16.1
-- 1.3.6.1.4.1.17409.1.16.1
		-- 1.3.6.1.4.1.17409.1.16.1
		cltConfigRemoteUpgradeNumber OBJECT-TYPE
			SYNTAX Integer32
			MAX-ACCESS read-only
			STATUS current
			DESCRIPTION
				"Description."
			::= { cltConfigRemoteUpgrade 1 }

		
--       1.3.6.1.4.1.17409.1.16.2
-- 1.3.6.1.4.1.17409.1.16.2
-- 1.3.6.1.4.1.17409.1.16.2
-- 1.3.6.1.4.1.17409.1.16.2
-- 1.3.6.1.4.1.17409.1.16.2
-- 1.3.6.1.4.1.17409.1.16.2
		-- 1.3.6.1.4.1.17409.1.16.2
		cltConfigRemoteUpgradeTable OBJECT-TYPE
			SYNTAX SEQUENCE OF CltConfigRemoteUpgradeEntry
			MAX-ACCESS not-accessible
			STATUS current
			DESCRIPTION
				"Description."
			::= { cltConfigRemoteUpgrade 2 }

		
--       1.3.6.1.4.1.17409.1.16.2.1
-- 1.3.6.1.4.1.17409.1.16.2.1
-- 1.3.6.1.4.1.17409.1.16.2.1
-- 1.3.6.1.4.1.17409.1.16.2.1
-- 1.3.6.1.4.1.17409.1.16.2.1
-- 1.3.6.1.4.1.17409.1.16.2.1
		-- 1.3.6.1.4.1.17409.1.16.2.1
		cltConfigRemoteUpgradeEntry OBJECT-TYPE
			SYNTAX CltConfigRemoteUpgradeEntry
			MAX-ACCESS not-accessible
			STATUS current
			DESCRIPTION
				"Description."
			INDEX { cltConfigRemoteUpgradeIndex }
			::= { cltConfigRemoteUpgradeTable 1 }

		
		CltConfigRemoteUpgradeEntry ::=
			SEQUENCE { 
				cltConfigRemoteUpgradeIndex
					Integer32,
				remoteUpgradeEnable
					Integer32,
				remoteUpgradeCurrentPcIP
					IpAddress,
				cltConfigRemoteUpgradeFileName
					OCTET STRING,
				remoteUpgradeUsername
					OCTET STRING,
				remoteUpgradePassword
					OCTET STRING,
				cltConfigRemoteUpgradeInterval
					Integer32,
				remoteUpgradeSubmit
					Integer32
			 }

--     1.3.6.1.4.1.17409.1.16.2.1.1
-- 1.3.6.1.4.1.17409.1.16.2.1.1
-- 1.3.6.1.4.1.17409.1.16.2.1.1
-- 1.3.6.1.4.1.17409.1.16.2.1.1
		-- 1.3.6.1.4.1.17409.1.16.2.1.1
		cltConfigRemoteUpgradeIndex OBJECT-TYPE
			SYNTAX Integer32
			MAX-ACCESS read-only
			STATUS current
			DESCRIPTION
				"Description."
			::= { cltConfigRemoteUpgradeEntry 1 }

		
--       1.3.6.1.4.1.17409.1.16.2.1.2
-- 1.3.6.1.4.1.17409.1.16.2.1.1
-- 1.3.6.1.4.1.17409.1.16.2.1.2
-- 1.3.6.1.4.1.17409.1.16.2.1.2
-- 1.3.6.1.4.1.17409.1.16.2.1.2
-- 1.3.6.1.4.1.17409.1.16.2.1.2
		-- 1.3.6.1.4.1.17409.1.16.2.1.2
		remoteUpgradeEnable OBJECT-TYPE
			SYNTAX Integer32
			MAX-ACCESS read-write
			STATUS current
			DESCRIPTION
				"Description."
			::= { cltConfigRemoteUpgradeEntry 2 }

		
--       1.3.6.1.4.1.17409.1.16.2.1.3
-- 1.3.6.1.4.1.17409.1.16.2.1.2
-- 1.3.6.1.4.1.17409.1.16.2.1.3
-- 1.3.6.1.4.1.17409.1.16.2.1.3
-- 1.3.6.1.4.1.17409.1.16.2.1.3
-- 1.3.6.1.4.1.17409.1.16.2.1.3
		-- 1.3.6.1.4.1.17409.1.16.2.1.3
		remoteUpgradeCurrentPcIP OBJECT-TYPE
			SYNTAX IpAddress
			MAX-ACCESS read-write
			STATUS current
			DESCRIPTION
				"Description."
			::= { cltConfigRemoteUpgradeEntry 3 }

		
--    1.3.6.1.4.1.17409.1.16.2.1.4
-- 1.3.6.1.4.1.17409.1.16.2.1.4
-- 1.3.6.1.4.1.17409.1.16.2.1.4
		-- 1.3.6.1.4.1.17409.1.16.2.1.4
		cltConfigRemoteUpgradeFileName OBJECT-TYPE
			SYNTAX OCTET STRING
			MAX-ACCESS read-write
			STATUS current
			DESCRIPTION
				"Description."
			::= { cltConfigRemoteUpgradeEntry 4 }

		
--       1.3.6.1.4.1.17409.1.16.2.1.4
-- 1.3.6.1.4.1.17409.1.16.2.1.3
-- 1.3.6.1.4.1.17409.1.16.2.1.4
-- 1.3.6.1.4.1.17409.1.16.2.1.5
-- 1.3.6.1.4.1.17409.1.16.2.1.5
-- 1.3.6.1.4.1.17409.1.16.2.1.5
		-- 1.3.6.1.4.1.17409.1.16.2.1.5
		remoteUpgradeUsername OBJECT-TYPE
			SYNTAX OCTET STRING
			MAX-ACCESS read-write
			STATUS current
			DESCRIPTION
				"Description."
			::= { cltConfigRemoteUpgradeEntry 5 }

		
--       1.3.6.1.4.1.17409.1.16.2.1.5
-- 1.3.6.1.4.1.17409.1.16.2.1.4
-- 1.3.6.1.4.1.17409.1.16.2.1.5
-- 1.3.6.1.4.1.17409.1.16.2.1.6
-- 1.3.6.1.4.1.17409.1.16.2.1.6
-- 1.3.6.1.4.1.17409.1.16.2.1.6
		-- 1.3.6.1.4.1.17409.1.16.2.1.6
		remoteUpgradePassword OBJECT-TYPE
			SYNTAX OCTET STRING
			MAX-ACCESS read-write
			STATUS current
			DESCRIPTION
				"Description."
			::= { cltConfigRemoteUpgradeEntry 6 }

		
--     1.3.6.1.4.1.17409.1.16.2.1.6
-- 1.3.6.1.4.1.17409.1.16.2.1.7
-- 1.3.6.1.4.1.17409.1.16.2.1.7
-- 1.3.6.1.4.1.17409.1.16.2.1.7
		-- 1.3.6.1.4.1.17409.1.16.2.1.7
		cltConfigRemoteUpgradeInterval OBJECT-TYPE
			SYNTAX Integer32
			MAX-ACCESS read-write
			STATUS current
			DESCRIPTION
				"Description."
			::= { cltConfigRemoteUpgradeEntry 7 }

		
--       1.3.6.1.4.1.17409.1.16.2.1.6
-- 1.3.6.1.4.1.17409.1.16.2.1.5
-- 1.3.6.1.4.1.17409.1.16.2.1.7
-- 1.3.6.1.4.1.17409.1.16.2.1.8
-- 1.3.6.1.4.1.17409.1.16.2.1.8
-- 1.3.6.1.4.1.17409.1.16.2.1.8
		-- 1.3.6.1.4.1.17409.1.16.2.1.8
		remoteUpgradeSubmit OBJECT-TYPE
			SYNTAX Integer32
			MAX-ACCESS read-write
			STATUS current
			DESCRIPTION
				"Description."
			::= { cltConfigRemoteUpgradeEntry 8 }

		
--         1.3.6.1.4.1.1.2
-- 1.3.6.1.4.1.17409.2
-- 1.3.6.1.4.1.17409.2
-- 1.3.6.1.4.1.17409.2
-- 1.3.6.1.4.1.17409.2
-- 1.3.6.1.4.1.17409.2
-- 1.3.6.1.4.1.17409.2
-- 1.3.6.1.4.1.17409.2
		-- 1.3.6.1.4.1.17409.2
		nscrtvRootConformance OBJECT IDENTIFIER ::= { nscrtvRoot 2 }

		
	
	END

--
-- 
--
